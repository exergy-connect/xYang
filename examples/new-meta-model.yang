module meta-model {
  yang-version 1.1;
  namespace "urn:xframe:meta-model";
  prefix "mm";

  organization "Exergy LLC";
  contact "Exergy.connect@gmail.com";
  description "YANG schema for the xFrame meta-model. This schema validates data model definition files (YAML/JSON) that define entities, fields, and relationships. Foreign keys always reference the primary key of the referenced entity.";

  revision "2026-03-29" {
    description
      "primitive-type-and-enum extended with min, max, minDate, maxDate under the primitive branch
       (legacy meta-model semantics; minDate/maxDate only for date or datetime primitive).";
  }

  revision "2026-03-28" {
    description
      "grouping primitive-type-and-enum (mandatory primitive + optional enum) shared by generic-field
       primitive cases and composite-subfields; enum only when primitive is string, integer, or number.";
  }

  revision "2026-03-27" {
    description
      "grouping field-default (leaf default) for entity fields and composite subcomponents;
       leaf required only on generic-field (not on composite subfields — inherited from parent).";
  }

  revision "2026-03-26" {
    description
      "grouping foreign-keys (list foreignKeys + entity leafref); uses foreign-keys { when ... }
       under type with not(../array) so foreignKeys is invalid when the type branch is array.";
  }

  revision "2026-03-24" {
    description "Recursive generic-field in composite parts; array elements primitive or composite.";
  }

  typedef primitive-type-name {
    type enumeration {
      enum string;
      enum integer;
      enum number;
      enum boolean;
      enum array;
      enum datetime;
      enum date;
      enum duration_in_days;
      enum qualified_string;
      enum qualified_integer;
      enum qualified_number;
    }
    description "Primitive field data type";
  }

  grouping primitive-type-and-enum {
    description
      "Primitive branch: type name, optional enum, and optional min/max / minDate/maxDate (legacy meta-model).
       enum applies only when primitive is string, integer, or number (when on enum).
       minDate and maxDate only when primitive is date or datetime.";
    leaf primitive {
      type primitive-type-name;
      mandatory true;
      description "Primitive type.";
    }
    leaf-list enum {
      when "../primitive = ('string', 'integer', 'number')";
      type union {
        type string;
        type int32;
        type decimal64 {
          fraction-digits 2;
        }
      }
      description
        "List of allowed values; only valid when primitive is string, integer, or number.";
    }
    leaf min {
      type int32;
      description
        "Minimum string length, or minimum value for integer/number primitives.";
    }
    leaf max {
      type int32;
      description
        "Maximum string length, or maximum value for integer/number primitives.";
    }
    leaf minDate {
      type date;
      description
        "Minimum date (YYYY-MM-DD) for date or datetime primitive fields.";
      must "../primitive = ('date','datetime')" {
        error-message "minDate can only be used with primitive type date or datetime";
        description "minDate applies only to date and datetime primitives.";
      }
      must "not(../maxDate) or . <= ../maxDate" {
        error-message "minDate must be less than or equal to maxDate when both are specified";
        description "Ordering between minDate and maxDate.";
      }
    }
    leaf maxDate {
      type date;
      description
        "Maximum date (YYYY-MM-DD) for date or datetime primitive fields.";
      must "../primitive = ('date','datetime')" {
        error-message "maxDate can only be used with primitive type date or datetime";
        description "maxDate applies only to date and datetime primitives.";
      }
      must "not(../minDate) or . >= ../minDate" {
        error-message "maxDate must be greater than or equal to minDate when both are specified";
        description "Ordering between minDate and maxDate.";
      }
    }
  }

  grouping field-default {
    description
      "Optional default value for instance data. Allowed on entity fields, field_definitions,
       and composite subcomponents; not combinable with required=true on the same node (see generic-field).";
    leaf default {
      type union {
        type string;
        type int32;
        type decimal64 {
          fraction-digits 2;
        }
        type boolean;
      }
      description "Default value when the field is omitted in instance data.";
    }
  }

  grouping foreign-keys {
    description
      "References to another entity by name; field value type must match that entity's primary key.
       Call sites use ``uses foreign-keys { when ... }`` so the condition applies in the parent type context.";
    list foreignKeys {
      key entity;
      min-elements 1;
      description "Each entry points at an entity whose primary key this field's type aligns with.";
      leaf entity {
        type leafref {
          path "/data-model/entities/name";
          require-instance true;
        }
        mandatory true;
        description "Referenced entity name.";
      }
      leaf parent_array {
        type leafref {
          path "/data-model/entities/fields/name";
          require-instance true;
        }
        description
          "Optional: Parent's array field name where children are nested. When specified, references a field on the referenced entity whose instance type includes a direct array branch (not only a field_definition reference).";
        must "/data-model/consolidated = false() or " +
           "count(/data-model/entities[name = string(deref(../entity))]/fields[name = current()]/type/array) = 1" {
          error-message
            "parent_array must name a field on the referenced entity whose type uses the array branch directly (not via field_definitions); skipped when consolidated is false.";
          description
            "Requires a direct type/array container on the referenced field. Fields that only reference field_definitions are not checked here. Skipped when consolidated is false.";
        }
      }
    }
  }

  grouping generic-field {
    description
      "Name, optional required (top-level only), container type, then optional default.
       Composite subcomponents use field-default only after type; required is inherited from the parent field.";
    leaf name {
      type string {
        length "1..128";
      }
      mandatory true;
      description "Field name.";
    }
    leaf required {
      type boolean;
      default false;
      description
        "Whether this field is required in instance data. Only for entity fields and field_definitions;
         must not appear on composite subcomponents (requiredness is inherited from the enclosing field).";
      must "not(../default) or . = false()" {
        error-message
          "A required field cannot have a default value. If required is true, default must not be specified.";
        description "A required field cannot have a default value.";
      }
    }
    container type {
      description "Field type: primitive, array or composite.";
      choice choice-type {
        mandatory true;
        description "Primitive, array of elements, or composite object.";
        case definition {
          leaf definition {
            type leafref {
              path "/data-model/entities/field_definitions/name";
              require-instance true;
            }
            mandatory true;
            description "Reference to a reusable field_definition name on this entity.";
          }
        }
        case primitive {
          uses primitive-type-and-enum;
        }
        case case-array {
          container array {
            description "Array field: homogeneous elements, each primitive or composite.";
            choice choice-type {
              mandatory true;
              description "Primitive, array of elements, or composite object.";
              case primitive {
                uses primitive-type-and-enum;
              }
              case case-composite {
                description "Composite field: named subfields, each a full generic-field.";
                uses composite-subfields;
              }
            }
          }
        }
        case case-composite {
          description "Composite field: named subfields, each a full generic-field.";
          uses composite-subfields;
        }
      }
      uses foreign-keys;
    }
    uses field-default;
  }

  grouping composite-subfields {
    description "Recursive generic-field entries as list items, with nesting limits.";
    list composite {
      key name;
      min-elements 1;
      description "Subfields (recursive generic field).";

      leaf name {
        type string {
          length "1..128";
        }
        mandatory true;
        description "Field name.";
      }
      container type {
        uses primitive-type-and-enum;
        uses foreign-keys {
          when "not(../array)";
        }
      }
      uses field-default;
    }
  }

// Root container for data model
  container data-model {
    description "Root container for data model definition";
    leaf consolidated {
      type boolean;
      default false;
      description "Consolidated validation flag. Set to true for Phase 2 (combined cross-file validation) or false for Phase 1 (individual file validation). When true, file-scoped constraints (field limits, name limits) are skipped as they were already validated per-file. Used by MUST constraints to conditionally apply file-scoped validations.";
    }
    leaf name {
      type string;
      description "Name of the data model";
    }
    leaf version {
      type version-string;
      description "Version string";
    }
    leaf author {
      type string;
      description "Author of the data model";
    }
    leaf source {
      type string;
      description "Optional documentation of where the model data comes from (e.g. URL, Excel file, API endpoint).";
    }
    leaf change_history {
      type change-history-policy;
      default 3;
      description
        "Default change history retention policy for all entities.
         Can be overridden per entity. Default: 3 (keep last 3 change ids)";
    }
    leaf include_x_fields {
      type boolean;
      default true;
      description
        "Include x-* extension fields in generated JSON Schema. When true, entity-level:
         x-primaryKey, x-created, x-modified, x-version, x-storage, x-validation.
         Field-level: x-primaryKey, x-foreignKey, x-parents, x-computed, x-confidence,
         x-source, x-minDate, x-maxDate.";
    }
    leaf allow_unlimited_fields {
      type empty;
      description "When present, allow entities to exceed the 7 non-array field limit. Omit when all entities have 7 or fewer non-array fields.";
      must "count(../entities[count(fields[type != 'array']) > 7]) > 0" {
        error-message "allow_unlimited_fields can only be set when at least one entity has more than 7 non-array fields. If all entities have 7 or fewer fields, omit this field.";
        description "When this flag is present, at least one entity must exceed the 7-field limit.";
      }
    }
    leaf max_name_underscores {
      type uint8;
      default 2;
      description "Maximum number of underscores allowed in entity and field names. Default is 2 (allowing names like 'entity_field_name' with max 3 components). This constraint helps maintain readable names and encourages proper entity boundaries. Names exceeding this limit suggest missing entity boundaries and should be restructured into separate entities with relationships.";
    }
    leaf-list exclude {
      type string;
      description "List of strings to exclude data files from ingestion";
    }
    list entities {
      key name;
      min-elements 1;
      description "List of entity definitions";
      leaf name {
        type entity-name;
        mandatory true;
        description "Entity name";
        must "string-length(.) - string-length(translate(., '_', '')) <= number(/data-model/max_name_underscores)" {
          error-message "Entity name exceeds the maximum underscore limit configured in max_name_underscores (default: 2). Deep names suggest missing entity boundaries - create proper entities instead.";
          description "Validates that entity name has at most max_name_underscores underscores (default: 2) to constrain hierarchical depth and reduce parsing complexity.";
        }
      }
      leaf brief {
        type string;
        description "Brief one-line summary of the entity";
      }
      leaf description {
        type string;
        description "AI-friendly description of the entity type, not mandatory but STRONGLY recommended";
      }
      leaf source {
        type string;
        description "Optional documentation of where this entity's data comes from (e.g. URL, Excel sheet, API endpoint).";
      }
      leaf primary_key {
        type leafref {
          path "../fields/name";
          require-instance true;
        }
        mandatory true;
        description "Primary key field for this entity. Can be a simple field or a composite field.";
      }
      leaf-list required_fields {
        type leafref {
          path "../fields/name";
          require-instance true;
        }
        description "List of required field names (auto-generated)";
      }
      must "/data-model/consolidated = true() or ../allow_unlimited_fields or count(fields[type != 'array']) <= 7" {
        error-message "Entity has more than 7 non-array fields. Array fields are excluded from this count as they represent relationships to child entities. Consider splitting into multiple entities with foreign key relationships, or set allow_unlimited_fields (present) to bypass this limit.";
        description "Validates that entity has at most 7 non-array fields, unless allow_unlimited_fields is present. Field limits are enforced in Phase 1 (individual file validation, consolidated=false) using the file's allow_unlimited_fields flag. In Phase 2 (combined validation, consolidated=true), this constraint is skipped as field limits are already validated per-file.";
      }
      list field_definitions {
        key name;
        description "Optional reusable field type and constraint definitions for this entity. Entity fields may reference these by setting type to this name; when type is a definition name, min, max, etc. must not be set inline. Names are unique within this entity only.";
        uses generic-field {
          refine type {
            must "not(./definition)" {
              error-message
                "A reusable field_definition cannot reference another field_definition; define the type with primitive, array, or composite only.";
              description
                "Disallows the definition leafref case under type so field_definitions do not chain or recurse via name references.";
            }
          }
        }
      }
      list fields {
        key name;
        min-elements 1;
        description "List of field definitions for this entity. Best practice: limit to 7 non-array fields per entity to encourage proper abstraction. Array fields (type: 'array') are excluded from this count as they represent relationships to child entities, not direct attributes. This constraint can be bypassed by setting allow_unlimited_fields (present) on the data model.";
        must "/data-model/consolidated = false() or count(/data-model/entities/field_definitions[name = current()/type]) = 0 or (not(current()/type/min) and not(current()/type/max) and not(current()/type/minDate) and not(current()/type/maxDate) and count(current()/type/enum) = 0 and not(current()/default) and not(current()/item_type) and count(current()/composite) = 0)" {
          error-message "When type references a field_definition, min, max, minDate, maxDate, enum, default, item_type, and composite must not be specified (description and brief may be used at the reference site).";
          description "Inline constraints only when type is a primitive; when type is a field_definition name they are inherited from the definition. Enforced only during consolidated validation (Phase 2). description and brief may be specified at the reference site.";
        }
        uses generic-field;
      }
      leaf change_history {
        type change-history-policy;
        description "Change history retention policy for this entity. Overrides model-level default.";
      }
      leaf v {
        type version-string;
        description "Model version of this entity, added during consolidation. NOTE: This field is automatically added during consolidation and should NOT be included in source YAML files.";
      }
      leaf c {
        type int32;
        description "Change ID when this entity was created. NOTE: This field is automatically added during consolidation and should NOT be included in source YAML files.";
        must "/data-model/consolidated = false() or /data-model/changes[id = current()]" {
          error-message "c must reference a valid change ID in the changes list";
          description "c must reference a valid change ID in the changes list. Only enforced during consolidated validation (Phase 2) when change IDs are available.";
        }
      }
      leaf-list m {
        type int32;
        description "List of change IDs when this entity was modified (history). The size of this list is controlled by the change_history policy.
                     NOTE: This field is automatically added during consolidation and should NOT be included in source YAML files.";
        must "/data-model/consolidated = false() or /data-model/changes[id = current()]" {
          error-message "Each m value must reference a valid change ID in the changes list";
          description "Each m value must reference a valid change ID in the changes list. Only enforced during consolidated validation (Phase 2) when change IDs are available.";
        }
      }
      leaf rate_of_change {
        type rate-of-change;
        description "Expected rate of change for this entity type, indicating what is considered 'normal' change frequency (e.g., hourly, daily, quarterly)";
      }
      leaf-list tools {
        type string;
        description "Optional list of tools that can provide additional details about this entity, such as real-time streaming telemetry or historical data";
      }
      leaf validation {
        type validation-mode;
        default strict;
        description "Data validation mode for this entity";
      }
      leaf storage {
        type storage-type;
        description "Storage type for entity data. INDEXED_KV uses CloudFlare Key-Value store with an index key (entityname:index) containing the primary key values of value keys (entityname:primary_key_1, ...). GITHUB_PR uses GitHub pull request storage.";
      }
    }
    list changes {
      key id;
      description "Change tracking records. NOTE: This list is automatically generated during consolidation and should NOT be included in source YAML files.";
      leaf id {
        type int32;
        mandatory true;
        description "Unique change identifier, monotonically increasing";
      }
      leaf timestamp {
        type date-and-time;
        mandatory true;
        description "ISO 8601 timestamp of the change";
      }
      leaf author {
        type string;
        description "Author of the change";
      }
      leaf note {
        type string;
        description "Optional note describing the change";
      }
      leaf git_commit_hash {
        type string;
        description "Git commit hash corresponding to this change";
      }
    }
  }
}
