module meta-model {
  yang-version 1.1;
  namespace "urn:xframe:meta-model";
  prefix "mm";

  organization "Exergy LLC";
  contact "Exergy.connect@gmail.com";
  description "YANG schema for the xFrame meta-model. This schema validates data model definition files (YAML/JSON) that define entities, fields, and relationships. Foreign keys reference the primary key of the referenced entity by default; optional ``field`` names a different target field that must be marked ``unique`` (alternate key).";

  revision "2026-05-05" {
    description
      "Leaf default on entity fields may use type/definition for site-specific values (with description and brief); consolidated must allows default at the reference site.
       When default is set with type/definition, the referenced field_definition must use open primitive or closed enum (not array, composite, or entity).";
  }

  revision "2026-04-14" {
    description
      "Broaden the shared entity-reference pattern for reuse beyond array fields and align its public name with that role.";
  }

  revision "2026-04-13" {
    description
      "Model references to entity types inside array-valued fields with a dedicated, typed pattern instead of ad hoc leaves.";
  }

  revision "2026-04-12" {
    description
      "field-unique: leaf unique only when not(../default) — alternate keys must not combine with default.";
  }

  revision "2026-04-11" {
    description
      "grouping field-unique (leaf unique); foreignKeys.field target must have unique true on the referenced entity.";
  }

  revision "2026-04-10" {
    description
      "foreignKeys: optional leaf ``field`` — leafref to a field on the referenced entity; must not equal that entity's primary_key.";
  }

  revision "2026-04-07" {
    description
      "field-default: leaf default only when type uses open-primitive or closed-enum (when type/primitive or type/enum).";
  }

  revision "2026-04-05" {
    description
      "field-default: optional must refinements so default matches closed-enum members or open-primitive family (array element + composite subfield).";
  }

  revision "2026-04-04" {
    description
      "primitive-type-and-enum: enforce open-primitive vs closed-enum with a YANG choice (not must-on-siblings). Data paths unchanged (case is not a data node).";
  }

  revision "2026-04-03" {
    description
      "primitive-type-and-enum: mutually exclusive primitive (open + min/max/minDate/maxDate/outlier) vs enum (closed list, implied type); flat leaves for JSON/YANG instance mapping.";
  }

  revision "2026-04-02" {
    description
      "primitive-type-name: add year; enum and min/max apply to year like integer.";
  }

  revision "2026-04-01" {
    description
      "Restored shared typedefs (date, entity-name, version-string, change-history-policy, rate-of-change, validation-mode, storage-type) for JSON Schema $defs;
       array choice array-element-entity; must expressions use type/array and type/definition paths.";
  }

  revision "2026-03-31" {
    description
      "Optional entity leaf index (type empty) for per-PK file sharding; forbidden when any field uses foreignKeys/parent_array.";
  }

  revision "2026-03-30" {
    description
      "Grouping field-common-atts (name, brief, mandatory description, source) reused by generic-field and composite-subfields;
       data-model and entity description leaves aligned with legacy meta-model (mandatory description on model and entity).";
  }

  revision "2026-03-29" {
    description
      "primitive-type-and-enum extended with min, max, minDate, maxDate under the primitive branch
       (legacy meta-model semantics; minDate/maxDate only for date or datetime primitive).";
  }

  revision "2026-03-28" {
    description
      "grouping primitive-type-and-enum (mandatory primitive + optional enum) shared by generic-field
       primitive cases and composite-subfields; enum only when primitive is string, integer, or number.";
  }

  revision "2026-03-27" {
    description
      "grouping field-default (leaf default) for entity fields and composite subcomponents;
       leaf required only on generic-field (not on composite subfields — inherited from parent).";
  }

  revision "2026-03-26" {
    description
      "grouping foreign-keys (list foreignKeys + entity leafref, optional field leafref to target field); uses foreign-keys { when ... }
       under type with not(../array) so foreignKeys is invalid when the type branch is array.";
  }

  revision "2026-03-24" {
    description "Recursive generic-field in composite parts; array elements primitive or composite.";
  }

  typedef primitive-type-name {
    type enumeration {
      enum string;
      enum integer;
      enum number;
      enum boolean;
      enum array;
      enum datetime;
      enum date;
      enum year;
      enum duration_in_days;
      enum qualified_string;
      enum qualified_integer;
      enum qualified_number;
    }
    description "Primitive field data type";
  }

  typedef date {
    type string {
      pattern '\d{4}-\d{2}-\d{2}';
    }
    description "Date in YYYY-MM-DD format";
  }

  typedef date-and-time {
    type string {
      pattern '\d{4}-\d{2}-\d{2}T\d{2}:\d{2}:\d{2}(\.\d+)?(Z|[+-]\d{2}:\d{2})?';
    }
    description "ISO 8601 date and time in format YYYY-MM-DDTHH:mm:ss[.sss][Z|±HH:mm]";
  }

  typedef entity-name {
    type string {
      length "1..64";
      pattern '[a-z_][a-z0-9_]*' {
        description
          "Entity names must start with a letter or underscore, followed by
           letters, digits, or underscores. They are normalized to lower case.";
      }
    }
    description "Entity name (letters, digits, underscores only, lowercase). The underscore count limit is configurable via max_name_underscores property (default: 2).";
  }

  typedef version-string {
    type string {
      pattern '\d{2}\.\d{2}\.\d{2}\.\d+' {
        description "Version format: YY.MM.DD.N where YY is 2-digit year, MM is month, DD is day, and N is sequence number";
      }
    }
    description "Version string in format YY.MM.DD.N, auto-incremented during consolidation when changes are detected";
  }

  typedef rate-of-change {
    type enumeration {
      enum hourly;
      enum daily;
      enum weekly;
      enum monthly;
      enum quarterly;
      enum yearly;
      enum rarely;
      enum never;
    }
    description "Expected rate of change for an entity, indicating what is considered 'normal' change frequency";
  }

  typedef validation-mode {
    type enumeration {
      enum strict;
      enum warn;
      enum skip;
    }
    description "Data validation mode for entity";
  }

  typedef storage-type {
    type enumeration {
      enum INDEXED_KV {
        description "CloudFlare Key-Value store with an index key (entityname:index) containing the primary key values of value keys (entityname:primary_key_1, ...)";
      }
      enum GITHUB_PR {
        description "GitHub pull request storage";
      }
    }
    description "Storage type for entity data";
  }

  typedef change-history-policy {
    type union {
      type int32 {
        range "0..max";
      }
      type string {
        pattern '\*';
      }
    }
    description
      "Change history retention policy. Can be:
       - An integer N: Keep last N modification change IDs (default: 3)
       - '*': Keep infinite history
       - 0: Disabled (no modification history tracked)";
  }

  typedef field-name {
    type string {
      length "1..128";
      pattern '[a-z_][a-z0-9_]*' {
        description
          "Field names must start with a letter or underscore, and are normalized to lower case.";
      }
    }
    description "Field name for computed references and leafrefs (same rules as entity fields).";
  }

  typedef field-validation-mode {
    type enumeration {
      enum enforce;
      enum filter;
    }
    description
      "Field validation mode. 'enforce' (default) — constraints are enforced during validation;
       'filter' — invalid field value is omitted from consolidated output.";
  }

  grouping primitive-type-and-enum {
    description
      "Open primitive (primitive plus optional min, max, minDate, maxDate, outlier) XOR closed enumeration (leaf-list enum).
       A YANG choice guarantees the branches are not combined. Instance paths stay type/primitive, type/min, … or type/enum (case is not a data node).";
    choice primitive-or-enum {
      mandatory true;
      description "Exactly one of open primitive typing or closed enum.";
      case open-primitive {
        leaf primitive {
          type primitive-type-name;
          mandatory true;
          description "Open primitive type.";
        }
        leaf min {
          type int32;
          description
            "Minimum string length, or minimum value for integer, number, or year primitives.";
        }
        leaf max {
          type int32;
          description
            "Maximum string length, or maximum value for integer, number, or year primitives.";
        }
        leaf minDate {
          type date;
          description
            "Minimum date (YYYY-MM-DD) for date or datetime primitive fields.";
          must "../primitive = ('date','datetime')" {
            error-message "minDate can only be used with primitive type date or datetime";
            description "minDate applies only to date and datetime primitives.";
          }
          must "not(../maxDate) or . <= ../maxDate" {
            error-message "minDate must be less than or equal to maxDate when both are specified";
            description "Ordering between minDate and maxDate.";
          }
        }
        leaf maxDate {
          type date;
          description
            "Maximum date (YYYY-MM-DD) for date or datetime primitive fields.";
          must "../primitive = ('date','datetime')" {
            error-message "maxDate can only be used with primitive type date or datetime";
            description "maxDate applies only to date and datetime primitives.";
          }
          must "not(../minDate) or . >= ../minDate" {
            error-message "maxDate must be greater than or equal to minDate when both are specified";
            description "Ordering between minDate and maxDate.";
          }
        }
        leaf outlier {
          when "not(../primitive = ('string', 'boolean', 'qualified_string'))";
          type decimal64 {
            fraction-digits 1;
            range "0.1..4.0";
          }
          description
            "Optional sigma multiplier for outlier flagging on numeric or date/datetime primitives.
             Omit to disable sigma-based outlier detection.";
        }
      }
      case closed-enum {
        leaf-list enum {
          min-elements 1;
          type union {
            type string;
            type int32;
            type decimal64 {
              fraction-digits 2;
            }
          }
          description
            "Closed enumeration; primitive (string, integer, or number) is implied from member types.";
        }
      }
    }
  }

  grouping field-default {
    description
      "Optional default value for instance data. Allowed on entity fields, field_definitions,
       and composite subcomponents; not combinable with required=true on the same node (see generic-field).
       Leaf default is conditional: when the sibling container type uses primitive, enum (open-type branch),
       or a field_definition reference whose resolved type is open primitive or closed enum (definition leafref).";
    leaf default {
      when
        "boolean(../type/primitive) or boolean(../type/enum) or boolean(../type/definition)";
      must
        "not(boolean(../type/definition)) or boolean(deref(../type/definition)/../type/primitive) or boolean(deref(../type/definition)/../type/enum)" {
        error-message
          "When type references a field_definition, default is only allowed if that definition uses an open primitive or closed enum (not array, composite, or entity).";
        description
          "Site-specific default at a definition reference is valid only for scalar reusable types.";
      }
      type union {
        type string;
        type int32;
        type decimal64 {
          fraction-digits 2;
        }
        type boolean;
      }
      description
        "Default value when the field is omitted in instance data. Valid for open primitive, closed enum,
         or type/definition when the referenced field_definition is itself primitive or enum.";
    }
  }

  grouping field-unique {
    description
      "Optional flag marking a field as an alternate key: values must be unique per entity instance set (in addition to primary key uniqueness). Required for targets of foreignKeys.field. Mutually exclusive with leaf default (no default may be specified on the same field).";
    leaf unique {
      when "not(../default)";
      type boolean;
      default false;
      description
        "When true, this field's values must be unique across all rows of the entity. Set on business or natural keys that may be referenced by foreignKeys.field on other entities. Only allowed when this field does not specify default (alternate keys must not use default).";
    }
  }

  grouping foreign-keys {
    description
      "References to another entity by name; the enclosing field's value type must match the referenced entity's primary key field, or the field named by ``field`` when that leaf is set (that target must declare ``unique`` true).
       Call sites use ``uses foreign-keys { when ... }``: omit when ``type`` uses scalar ``entity`` (target is already named there).";
    list foreignKeys {
      key entity;
      description "Each entry points at an entity; values align with primary key unless ``field`` specifies another target field (which must be marked ``unique`` on the referenced entity).";
      uses entity-reference;
      leaf field {
        type leafref {
          path "/data-model/entities[name = current()/../entity]/fields/name";
          require-instance true;
        }
        description
          "Optional: names a field on the referenced entity that this foreign key's value must match. When omitted, the referenced entity's primary key is used. Must not name the primary key (use omission for that case). When set, the named field must declare ``unique`` true (alternate key).";
        must "/data-model/consolidated = false() or string(.) != string(/data-model/entities[name = string(deref(../entity))]/primary_key)" {
          error-message
            "field must not name the referenced entity's primary key; omit field to reference the primary key.";
          description
            "When present, field must differ from the target entity's primary_key. Entity key via deref(../entity). Skipped when consolidated is false.";
        }
        must "/data-model/consolidated = false() or boolean(deref(.)/../unique) = true()" {
          error-message
            "field must name a field on the referenced entity with unique true (alternate key). Set unique: true on that field in the model.";
          description
            "Non-primary foreign key targets must be explicitly marked unique: follow this leafref with deref(.) to fields/name, then sibling ../unique. Skipped when consolidated is false.";
        }
      }
      leaf parent_array {
        type leafref {
          path "/data-model/entities/fields/name";
          require-instance true;
        }
        description
          "Optional: Parent's array field name where children are nested. When specified, references a field on the referenced entity whose instance type includes a direct array branch (not only a field_definition reference).";
        must "/data-model/consolidated = false() or " +
           "count(/data-model/entities[name = string(deref(../entity))]/fields[name = current()]/type/array) = 1" {
          error-message
            "parent_array must name a field on the referenced entity whose type uses the array branch directly (not via field_definitions); skipped when consolidated is false.";
          description
            "Requires a direct type/array container on the referenced field. Fields that only reference field_definitions are not checked here. Skipped when consolidated is false.";
        }
      }
    }
  }

  grouping entity-reference {
    description
      "Leaf ``entity``: leafref to /data-model/entities/name. Reused where the model names a target entity.";
    leaf entity {
      type leafref {
        path "/data-model/entities/name";
        require-instance true;
      }
      mandatory true;
      description "Referenced entity name.";
    }
  }

  grouping field-common-atts {
    description
      "Shared name and documentation attributes for entity fields, field_definitions, and composite subcomponents.
       When type references a field_definition, brief and description may be specified at the reference site to override or supplement the definition.";
    leaf name {
      type string {
        length "1..128";
      }
      mandatory true;
      description "Field name.";
    }
    leaf brief {
      type string;
      description
        "Brief one-line summary of the field. When type references a field_definition, may be specified at the reference site to override or supplement the definition's brief.";
    }
    leaf description {
      type string;
      mandatory true;
      description
        "AI-friendly field description. When type references a field_definition, may be specified at the reference site to override or supplement the definition's description.";
    }
    leaf source {
      type string;
      description
        "Optional documentation of where this field's data comes from (e.g. URL, Excel column name, API path).";
    }
  }

  grouping generic-field {
    description
      "uses field-common-atts (name, brief, description, source); optional required (top-level only); container type; optional default.
       Composite subcomponents use field-default only after type; required is inherited from the parent field.";
    uses field-common-atts;
    leaf required {
      type boolean;
      default false;
      description
        "Whether this field is required in instance data. Only for entity fields and field_definitions;
         must not appear on composite subcomponents (requiredness is inherited from the enclosing field).";
      must "not(../default) or . = false()" {
        error-message
          "A required field cannot have a default value. If required is true, default must not be specified.";
        description "A required field cannot have a default value.";
      }
    }
    container type {
      description "Field type: primitive, array or composite.";
      choice choice-type {
        mandatory true;
        description "Primitive, array of elements, or composite object.";
        case definition {
          leaf definition {
            type leafref {
              path "/data-model/entities/field_definitions/name";
              require-instance true;
            }
            mandatory true;
            description "Reference to a reusable field_definition name on this entity.";
          }
        }
        case open-type {
          description
            "Primitive or closed enum (leaf primitive or leaf-list enum). Case name avoids clashing with leaf primitive in JSON.";
          uses primitive-type-and-enum;
        }
        case entity-type {
          uses entity-reference;
        }
        case case-array {
          container array {
            description "Array field: homogeneous elements, each primitive or composite.";
            choice choice-type {
              mandatory true;
              description "Primitive, array of elements, or composite object.";
              case open-type {
                description "Array element: primitive or closed enum; case name avoids clashing with leaf primitive.";
                uses primitive-type-and-enum;
              }
              case array-element-entity {
                uses entity-reference;
              }
              case case-composite {
                description "Composite field: named subfields, each a full generic-field.";
                uses composite-subfields;
              }
            }
          }
        }
        case case-composite {
          description "Composite field: named subfields, each a full generic-field.";
          uses composite-subfields;
        }
      }
      uses foreign-keys {
        when "not(boolean(./entity))";
      }
    }
    uses field-default;
    uses field-unique;
    leaf validation {
      type field-validation-mode;
      default enforce;
      description
        "Per-field validation: enforce constraints or filter invalid values from consolidated output.";
    }
    container computed {
      presence "Computed field is defined";
      description
        "When present, the field value is derived from referenced fields using the given operation.
         Computed fields are read-only in JSON Schema and excluded from required_fields.";
      leaf operation {
        type enumeration {
          enum add {
            description "Add: fields[0] + fields[1]. Integer/number; exactly 2 fields.";
          }
          enum subtraction {
            description "Subtract: fields[0] - fields[1]. date/datetime or integer/number; 2 fields.";
          }
          enum multiplication {
            description "Multiply: fields[0] * fields[1]. Integer/number; exactly 2 fields.";
          }
          enum division {
            description "Divide: fields[0] / fields[1]. Integer/number; exactly 2 fields.";
          }
          enum min {
            description "Minimum of all referenced fields. date, datetime, integer, number; 2+ fields.";
          }
          enum max {
            description "Maximum of all referenced fields. date, datetime, integer, number; 2+ fields.";
          }
          enum average {
            description "Mean of numeric fields. integer/number only; 2+ fields.";
          }
        }
        mandatory true;
        description "Operation applied to referenced fields.";
      }
      list fields {
        key field;
        min-elements 2;
        max-elements 100;
        description "Field references for the computation (same entity or cross-entity with entity leaf).";
        leaf field {
          type field-name;
          mandatory true;
          description "Referenced field name.";
          must "/data-model/consolidated = false() or ((not(../entity) and count(../../../../fields[name = current()]) = 1) or (../entity and count(deref(../entity)/../fields[name = current()]) = 1))" {
            error-message "Computed field reference must exist in the specified entity (or current entity if not specified)";
            description "Validates that the field exists: in current entity when entity is omitted, or in referenced entity when entity is specified. Only enforced during consolidated validation (Phase 2) when cross-file references can be resolved.";
          }
        }
        uses entity-reference {
          refine entity {
            mandatory false;
            description "Entity name for cross-entity field reference (optional).";
            must "/data-model/consolidated = false() or count(../../../../fields[type/foreignKeys/entity = current()]) = 1" {
              error-message "Cross-entity computed field references require a foreign key field in the current entity that references the target entity";
              description "When entity is specified, there must be exactly one field in the current entity with a foreignKeys referencing this entity. Only enforced during consolidated validation (Phase 2) when cross-file references can be resolved.";
            }
          }
        }
        must "../../operation != 'average' or (not(current()/entity) and ../../../fields[name = current()/field]/type/primitive = ('integer', 'number')) or (current()/entity and /data-model/entities[name = current()/entity]/fields[name = current()/field]/type/primitive = ('integer', 'number'))" {
          error-message "Average operation requires all referenced fields to have type integer or number";
          description "When operation is average, each referenced field (same-entity or cross-entity) must be numeric (integer or number). Only enforced during consolidated validation (Phase 2).";
        }
      }
      must "(operation != 'add' and operation != 'subtraction') or count(fields) = 2" {
        error-message "Binary operations (add, subtraction) require exactly 2 fields";
        description "Validates that binary operations have exactly 2 field references";
      }
      must "(operation != 'min' and operation != 'max' and operation != 'average') or count(fields) >= 2" {
        error-message "Aggregation operations (min, max, average) require at least 2 fields";
        description "Validates that aggregation operations have at least 2 field references";
      }
    }
  }

  grouping composite-subfields {
    description "Recursive generic-field entries as list items, with nesting limits.";
    list composite {
      key name;
      min-elements 1;
      description "Subfields (recursive generic field).";

      uses field-common-atts;
      container type {
        choice composite-subfield-type {
          mandatory true;
          description "Primitive/closed enum or scalar entity reference (same shape as generic-field entity-type).";
          case open-type {
            description "Primitive or closed enum; case name avoids clashing with leaf primitive in JSON.";
            uses primitive-type-and-enum;
          }
          case entity-type {
            uses entity-reference;
          }
        }
        uses foreign-keys {
          when "not(boolean(./entity))";
        }
      }
      uses field-default;
    }
  }

// Root container for data model
  container data-model {
    description "Root container for data model definition";
    leaf consolidated {
      type boolean;
      default false;
      description "Consolidated validation flag. Set to true for Phase 2 (combined cross-file validation) or false for Phase 1 (individual file validation). When true, file-scoped constraints (field limits, name limits) are skipped as they were already validated per-file. Used by MUST constraints to conditionally apply file-scoped validations.";
    }
    leaf name {
      type string;
      description "Name of the data model";
    }
    leaf version {
      type version-string;
      description "Version string";
    }
    leaf author {
      type string;
      description "Author of the data model";
    }
    leaf description {
      type string;
      mandatory true;
      description "AI-friendly description of the overall data model, its purpose, and main entities.";
    }
    leaf source {
      type string;
      description "Optional documentation of where the model data comes from (e.g. URL, Excel file, API endpoint).";
    }
    leaf change_history {
      type change-history-policy;
      default 3;
      description
        "Default change history retention policy for all entities.
         Can be overridden per entity. Default: 3 (keep last 3 change ids)";
    }
    leaf include_x_fields {
      type boolean;
      default true;
      description
        "Include x-* extension fields in generated JSON Schema. When true, entity-level:
         x-primaryKey, x-created, x-modified, x-version, x-storage, x-validation.
         Field-level: x-primaryKey, x-foreignKey, x-parents, x-computed, x-confidence,
         x-source, x-minDate, x-maxDate.";
    }
    leaf allow_unlimited_fields {
      type empty;
      description "When present, allow entities to exceed the 7 non-array field limit. Omit when all entities have 7 or fewer non-array fields.";
      must "count(../entities[count(fields[not(type/array)]) > 7]) > 0" {
        error-message "allow_unlimited_fields can only be set when at least one entity has more than 7 non-array fields. If all entities have 7 or fewer fields, omit this field.";
        description "When this flag is present, at least one entity must exceed the 7-field limit.";
      }
    }
    leaf max_name_underscores {
      type uint8;
      default 2;
      description "Maximum number of underscores allowed in entity and field names. Default is 2 (allowing names like 'entity_field_name' with max 3 components). This constraint helps maintain readable names and encourages proper entity boundaries. Names exceeding this limit suggest missing entity boundaries and should be restructured into separate entities with relationships.";
    }
    leaf-list exclude {
      type string;
      description "List of strings to exclude data files from ingestion";
    }
    list entities {
      key name;
      min-elements 1;
      description "List of entity definitions";
      leaf index {
        type empty;
        must "count(../fields[type/foreignKeys[parent_array]]) = 0" {
          error-message "index can only be set on top-level entities. Remove index or remove parent_array from this entity's foreignKeys.";
          description "Disallow index on entities that define parent relationships via foreignKeys/parent_array (nested child entities).";
        }
        description
          "When present, consolidation writes one JSON file per primary-key instance under
           output/<entity-name>/ (readable, filesystem-safe form of the entity-store PK string,
           .json).
           Shards duplicate top-level nested instances after hierarchical nesting; the same
           records remain in consolidated_data.json data. sharded_entities lists those type
           names.";
      }
      leaf name {
        type entity-name;
        mandatory true;
        description "Entity name";
        must "string-length(.) - string-length(translate(., '_', '')) <= number(/data-model/max_name_underscores)" {
          error-message "Entity name exceeds the maximum underscore limit configured in max_name_underscores (default: 2). Deep names suggest missing entity boundaries - create proper entities instead.";
          description "Validates that entity name has at most max_name_underscores underscores (default: 2) to constrain hierarchical depth and reduce parsing complexity.";
        }
      }
      leaf brief {
        type string;
        description "Brief one-line summary of the entity";
      }
      leaf description {
        type string;
        mandatory true;
        description "AI-friendly description of the entity type.";
      }
      leaf source {
        type string;
        description "Optional documentation of where this entity's data comes from (e.g. URL, Excel sheet, API endpoint).";
      }
      leaf primary_key {
        type leafref {
          path "../fields/name";
          require-instance true;
        }
        mandatory true;
        description "Primary key field for this entity. Can be a simple field or a composite field.";
      }
      leaf-list required_fields {
        type leafref {
          path "../fields/name";
          require-instance true;
        }
        description "List of required field names (auto-generated)";
      }
      must "/data-model/consolidated = true() or ../allow_unlimited_fields or count(fields[not(type/array)]) <= 7" {
        error-message "Entity has more than 7 non-array fields. Array fields are excluded from this count as they represent relationships to child entities. Consider splitting into multiple entities with foreign key relationships, or set allow_unlimited_fields (present) to bypass this limit.";
        description "Validates that entity has at most 7 non-array fields, unless allow_unlimited_fields is present. Field limits are enforced in Phase 1 (individual file validation, consolidated=false) using the file's allow_unlimited_fields flag. In Phase 2 (combined validation, consolidated=true), this constraint is skipped as field limits are already validated per-file.";
      }
      list field_definitions {
        key name;
        description "Optional reusable field type and constraint definitions for this entity. Entity fields may reference these by setting type to this name; when type is a definition name, min, max, etc. must not be set inline. Names are unique within this entity only.";
        uses generic-field {
          refine type {
            must "not(./definition)" {
              error-message
                "A reusable field_definition cannot reference another field_definition; define the type with primitive, array, or composite only.";
              description
                "Disallows the definition leafref case under type so field_definitions do not chain or recurse via name references.";
            }
          }
        }
      }
      list fields {
        key name;
        min-elements 1;
        description "List of field definitions for this entity. Best practice: limit to 7 non-array fields per entity to encourage proper abstraction. Array fields (type: 'array') are excluded from this count as they represent relationships to child entities, not direct attributes. This constraint can be bypassed by setting allow_unlimited_fields (present) on the data model.";
        must "/data-model/consolidated = false() or count(/data-model/entities/field_definitions[name = current()/type/definition]) = 0 or (not(current()/type/min) and not(current()/type/max) and not(current()/type/minDate) and not(current()/type/maxDate) and count(current()/type/enum) = 0 and count(current()/type/array) = 0 and count(current()/type/composite) = 0)" {
          error-message "When type references a field_definition, min, max, minDate, maxDate, enum, array, composite, and other inline type branches must not be specified (description, brief, and default may be used at the reference site).";
          description "Inline type constraints are inherited from the definition; when type uses the definition leafref do not repeat primitive branches at the reference site. Enforced only during consolidated validation (Phase 2). description, brief, and optional default may be specified at the reference site.";
        }
        uses generic-field;
      }
      leaf change_history {
        type change-history-policy;
        description "Change history retention policy for this entity. Overrides model-level default.";
      }
      leaf v {
        type version-string;
        description "Model version of this entity, added during consolidation. NOTE: This field is automatically added during consolidation and should NOT be included in source YAML files.";
      }
      leaf c {
        type int32;
        description "Change ID when this entity was created. NOTE: This field is automatically added during consolidation and should NOT be included in source YAML files.";
        must "/data-model/consolidated = false() or /data-model/changes[id = current()]" {
          error-message "c must reference a valid change ID in the changes list";
          description "c must reference a valid change ID in the changes list. Only enforced during consolidated validation (Phase 2) when change IDs are available.";
        }
      }
      leaf-list m {
        type int32;
        description "List of change IDs when this entity was modified (history). The size of this list is controlled by the change_history policy.
                     NOTE: This field is automatically added during consolidation and should NOT be included in source YAML files.";
        must "/data-model/consolidated = false() or /data-model/changes[id = current()]" {
          error-message "Each m value must reference a valid change ID in the changes list";
          description "Each m value must reference a valid change ID in the changes list. Only enforced during consolidated validation (Phase 2) when change IDs are available.";
        }
      }
      leaf rate_of_change {
        type rate-of-change;
        description "Expected rate of change for this entity type, indicating what is considered 'normal' change frequency (e.g., hourly, daily, quarterly)";
      }
      leaf-list tools {
        type string;
        description "Optional list of tools that can provide additional details about this entity, such as real-time streaming telemetry or historical data";
      }
      leaf validation {
        type validation-mode;
        default strict;
        description "Data validation mode for this entity";
      }
      leaf storage {
        type storage-type;
        description "Storage type for entity data. INDEXED_KV uses CloudFlare Key-Value store with an index key (entityname:index) containing the primary key values of value keys (entityname:primary_key_1, ...). GITHUB_PR uses GitHub pull request storage.";
      }
    }
    list changes {
      key id;
      description "Change tracking records. NOTE: This list is automatically generated during consolidation and should NOT be included in source YAML files.";
      leaf id {
        type int32;
        mandatory true;
        description "Unique change identifier, monotonically increasing";
      }
      leaf timestamp {
        type date-and-time;
        mandatory true;
        description "ISO 8601 timestamp of the change";
      }
      leaf author {
        type string;
        description "Author of the change";
      }
      leaf note {
        type string;
        description "Optional note describing the change";
      }
      leaf git_commit_hash {
        type string;
        description "Git commit hash corresponding to this change";
      }
    }
  }
}
