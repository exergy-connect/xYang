module minimal-parents-test {
  namespace "urn:test:minimal-parents";
  prefix "mpt";
  yang-version 1.1;

  container data-model {
    leaf consolidated {
      type boolean;
      default false;
    }

    list entities {
      key name;
      leaf name {
        type string;
      }

      leaf-list primary_key {
        type string;
      }

      list fields {
        key name;
        leaf name {
          type string;
        }
        leaf type {
          type string;
        }
        container foreignKey {
          presence "Foreign key is defined";
          leaf entity {
            type leafref {
              path "/data-model/entities/name";
              require-instance true;
            }
            mandatory true;
          }
          leaf field {
            type leafref {
              path "/data-model/entities/fields/name";
              require-instance true;
            }
            mandatory true;
          }
        }
      }

      list parents {
        key child_fk;
        leaf child_fk {
          type leafref {
            path "../../fields/name";
            require-instance true;
          }
          mandatory true;
          description "Child foreign key field name";

          // Test 1: Entity existence check (FIXED - using path expression)
          must "/data-model/consolidated = false() or /data-model/entities[name = deref(current())/../foreignKey/entity]" {
            error-message "Foreign key entity must exist in the data model";
          }

          // Test 2: Field existence check (FIXED - using path expression)
          must "/data-model/consolidated = false() or /data-model/entities[name = deref(current())/../foreignKey/entity]/fields[name = deref(current())/../foreignKey/field]" {
            error-message "Foreign key field must exist in the referenced entity's fields";
          }

          // Test 3: Primary key existence check (FIXED - using path expression)
          must "/data-model/consolidated = false() or /data-model/entities[name = deref(current())/../foreignKey/entity]/primary_key" {
            error-message "Parent entity must have a primary key defined";
          }

          // Test 4: FK references PK check (FIXED - using path expression)
          must "/data-model/consolidated = false() or /data-model/entities[name = deref(current())/../foreignKey/entity]/primary_key[. = deref(current())/../foreignKey/field]" {
            error-message "Foreign key field must reference one of the parent entity's primary key fields";
          }

          // Test 5: Type matching check (WORKING - using nested deref)
          // must "/data-model/consolidated = false() or deref(current())/../type = " +
          //      "deref(deref(current())/../foreignKey/entity)/../fields[name = deref(current())/../foreignKey/field]/type" {
          //   error-message "Child foreign key field type must match parent primary key field type";
          // }

          // Test 5: Type matching check (FAILING - using path expression)
          must "/data-model/consolidated = false() or deref(current())/../type = " +
               "/data-model/entities[name = deref(current())/../foreignKey/entity]/fields[name = deref(current())/../foreignKey/field]/type" {
            error-message "Child foreign key field type must match parent primary key field type";
          }
        }

        leaf parent_array {
          type leafref {
            path "/data-model/entities/fields/name";
            require-instance true;
          }
          mandatory true;
          description "Parent's array field name";

          // Test 6: Parent array existence check (WORKING - using nested deref)
          // must "/data-model/consolidated = false() or deref(deref(../child_fk)/../foreignKey/entity)/../fields[name = current()]" {
          //   error-message "Parent array field must exist in the parent entity's fields";
          // }

          // Test 6: Parent array existence check (FAILING - using path expression)
          must "/data-model/consolidated = false() or /data-model/entities[name = deref(../child_fk)/../foreignKey/entity]/fields[name = current()]" {
            error-message "Parent array field must exist in the parent entity's fields";
          }

          // Test 7: Parent array type check (WORKING - using nested deref)
          // must "/data-model/consolidated = false() or deref(deref(../child_fk)/../foreignKey/entity)/../fields[name = current()]/type = 'array'" {
          //   error-message "Parent array field must be of type 'array'";
          // }

          // Test 7: Parent array type check (FAILING - using count with filter)
          must "/data-model/consolidated = false() or " +
               "count(/data-model/entities[name = deref(../child_fk)/../foreignKey/entity]/fields[name = current() and type = 'array']) > 0" {
            error-message "Parent array field must be of type 'array'";
          }
        }
      }
    }
  }
}
