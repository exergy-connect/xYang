module example-mcp {
  yang-version 1.1;
  namespace "urn:example:mcp";
  prefix mcp;
  organization "xYang example authors";
  contact "https://github.com/exergy-connect/xYang";
  description
    "Base model for an MCP server interface and a session of tools/call
     requests, as seen by one side.

     A tool is declared twice from one source: as a YANG rpc (which
     compile_mcp.py turns into a standard MCP tools/list entry) and as an
     identity derived from 'tool' (which a session's calls must name).
     A tool module instantiates the 'session' grouping as its top-level
     container and augments call/arguments with one container per tool,
     gated by 'when' on the call's tool identity.

     MCP 2026-07-28 has no protocol-level session. A server that keeps
     state across calls mints an explicit handle from a creation tool and
     takes it as an ordinary argument on later calls. This module supplies
     the handle type, the argument every tool uses, and the output of the
     tool that mints it. The 'http-header' extension marks the argument to
     be mirrored into an HTTP header (MCP x-mcp-header), so intermediaries
     can route a call to its session without parsing the body.

     A valid session is consistent with its own calls. It is a local view:
     it says nothing about state outside this document.
     SPDX-License-Identifier: MIT";
  reference "RFC 7950; RFC 7951; Model Context Protocol 2026-07-28, server/tools (Stateful Tools, x-mcp-header)";
  revision 2026-11-11 { description "Initial example revision.";
    reference "xYang examples/mcp-interface/README.md"; }

  identity tool {
    description "Base of every MCP tool. A tool module derives one identity per rpc, with the same name.";
  }

  extension http-header {
    argument name;
    description
      "Mirror this tool argument into the HTTP header Mcp-Param-<name> on the
       Streamable HTTP transport. compile_mcp.py emits it as the property's
       x-mcp-header. Only for string, integer and boolean leaves directly
       below the rpc input.";
    reference "Model Context Protocol 2026-07-28, server/tools, x-mcp-header";
  }

  typedef session-handle {
    type string { pattern 'ses_[0-9a-f]{32}'; }
    description
      "Opaque handle minted by the server's session-creating tool: 'ses_'
       followed by 128 random bits in hex. It is a bearer token on an
       unauthenticated server, so it carries no structure.";
  }

  grouping session-argument {
    description "The handle argument every stateful tool takes.";
    leaf session {
      type mcp:session-handle;
      mandatory true;
      mcp:http-header "Session";
      description "Handle returned by open-session. Sessions expire after 24 hours without a call.";
    }
  }

  grouping session-created {
    description "Output of the tool that mints a session handle.";
    leaf session {
      type mcp:session-handle;
      mandatory true;
      description "Pass this handle as 'session' on every later call.";
    }
  }

  typedef sha256-hex {
    type string { pattern '[0-9a-f]{64}'; }
    description "Lowercase hexadecimal SHA-256 digest.";
  }

  grouping session {
    description
      "Server identity, the local view the session was checked in, and the
       tools/call requests made. A tool module instantiates it as its own
       top-level 'session' container and augments call/arguments.";

    leaf handle {
      type mcp:session-handle;
      mandatory true;
      description "The handle this record is kept under.";
    }

    leaf protocol-version {
      type string { pattern '[0-9]{4}-[0-9]{2}-[0-9]{2}'; }
      mandatory true;
      description "MCP protocol revision the calls were made in.";
    }

    container server {
      description "serverInfo the server reports in each result's _meta.";
      leaf name { type string { length "1..128"; } mandatory true; description "Server name."; }
      leaf version { type string { length "1..64"; } mandatory true; description "Server version."; }
    }

    container view {
      description
        "The local context this record was checked in. No validator has a global
         view, so a verdict names the view it was made in.";
      leaf caller { type string { length "1..128"; } mandatory true; description "Who made the calls."; }
      leaf snapshot { type sha256-hex; mandatory true; description "Digest of the server-side context the calls ran against."; }
    }

    list call {
      key "id";
      description "One tools/call request and its outcome, in the order sent. A session starts with none.";

      leaf id {
        type uint32;
        description "Sequence number the server assigns in receive order, so rules compare ids to mean 'earlier'.";
      }
      leaf tool {
        type identityref { base mcp:tool; }
        mandatory true;
        description "params.name of the request, as a tool identity. An undeclared tool is rejected here.";
      }
      container arguments {
        must "count(*) = 1" {
          error-message "arguments must hold exactly one container: the one for the called tool.";
        }
        description
          "params.arguments. Tool modules augment one container per tool. A call
           carries the called tool's container, even when it is empty, so a
           missing or extra one is caught here without this module knowing
           which tools exist.";
      }
      container result {
        description "Outcome of the call.";
        leaf status {
          type enumeration {
            enum ok { description "result.isError is false or absent."; }
            enum error { description "result.isError is true, or a JSON-RPC error."; }
          }
          mandatory true;
          description "Whether the call succeeded.";
        }
        leaf message { type string; description "Error text when status is error."; }
      }
    }
  }
}
