module example-audit {
  yang-version 1.1;
  namespace "urn:example:audit";
  prefix audit;
  import example-hypergraph { prefix hg; revision-date 2026-11-10; }
  import example-bfo { prefix bfo; revision-date 2026-11-10; }
  organization "xYang example authors";
  contact "https://github.com/exergy-connect/xYang";
  description
    "Fictional audit engagement profile in one model: client facts (employees,
     accounts, terminations, account use, privileged changes), controls,
     collected evidence, assessments, findings, and reviews.

     Every conclusion must agree with the facts in the same tree. A record that
     reports a real breach as an exception is valid; a record that hides it or
     invents one is not. A valid tree is a consistent record, not an audit
     opinion, and says nothing about whether the facts themselves are true.

     Times are uint32 seconds since 1970-01-01T00:00:00Z (UTC) so that must
     expressions can compare and add them as numbers.
     SPDX-License-Identifier: MIT";
  reference "RFC 7950; RFC 7951; xYang examples/ontology-hypergraph/README.md";
  revision 2026-11-10 { description "Initial example revision.";
    reference "xYang examples/ontology-hypergraph/README.md"; }

  typedef epoch-seconds {
    type uint32;
    units "seconds since 1970-01-01T00:00:00Z";
    description
      "UTC time as a JSON number. XPath compares these exactly: every
       uint32 value is an exact IEEE 754 double.";
  }

  identity engagement { base bfo:process; description "An audit engagement for one client and period."; }
  identity control { base bfo:continuant; description "A client control statement in the firm catalogue."; }
  identity evidence-record { base bfo:continuant; description "A collected client artifact, such as a system export."; }
  identity source-system { base bfo:continuant; description "A client system that produced evidence."; }
  identity employee { base bfo:material-entity; description "A client employee."; }
  identity account { base bfo:continuant; description "A client system account owned by one employee."; }
  identity termination-event { base bfo:process; description "An employee's termination taking effect."; }
  identity account-use-event { base bfo:process; description "A recorded use of an account."; }
  identity change-event { base bfo:process; description "A privileged production change."; }
  identity actor { base bfo:continuant; description "A participant in the engagement."; }
  identity collection-agent { base actor; description "Software that collects client evidence."; }
  identity practitioner { base actor; description "May assess controls."; }
  identity assessment-agent { base practitioner; description "Software that drafts assessments."; }
  identity audit-professional { base bfo:material-entity; description "A person on the engagement team; may assess and review."; }

  identity control-rule { description "Which client facts decide a control's outcome."; }
  identity leaver-access { base control-rule; description "No account is used after its owner's termination."; }
  identity change-approval {
    base control-rule;
    description "Each privileged change is approved by someone other than the implementer, no later than deployment.";
  }
  identity manual-review { base control-rule; description "No facts in this model decide the outcome."; }

  identity evidence-type { description "Kind of collected artifact."; }
  identity hr-termination-report { base evidence-type; description "Leavers exported from the HR system."; }
  identity sign-in-log { base evidence-type; description "Account sign-ins exported from identity management."; }
  identity change-ticket-export { base evidence-type; description "Change tickets with approvals."; }
  identity deployment-log { base evidence-type; description "Production deployment records."; }
  identity access-review-record { base evidence-type; description "Signed quarterly access review."; }

  identity collection { base hg:relation; description "Evidence collected from one source system."; }
  identity assessment { base hg:relation; description "Conclusion on one control for one engagement."; }
  identity review { base hg:relation; description "Independent sign-off of one assessment."; }
  identity finding { base hg:relation; description "Reportable exception based on one assessment."; }
  identity workpaper-bundle { base hg:relation; description "Unconstrained grouping of records."; }

  identity collector { base hg:role; description "Collecting agent."; }
  identity source { base hg:role; description "System the evidence came from."; }
  identity collected { base hg:role; description "Evidence produced by a collection."; }
  identity in-engagement { base hg:role; description "Engagement the record belongs to."; }
  identity assessor { base hg:role; description "Practitioner who concluded."; }
  identity assessed-control { base hg:role; description "Control concluded on."; }
  identity cited-evidence { base hg:role; description "Evidence relied on."; }
  identity reviewer { base hg:role; description "Independent human reviewer."; }
  identity reviewed { base hg:role; description "Assessment under review."; }
  identity basis { base hg:role; description "Assessment a finding is based on."; }
  identity violation { base hg:role; description "Fact that breaches the control."; }
  identity member { base hg:role; description "Bundled record."; }

  container graph {
    presence "A local graph projection is supplied.";
    description "Collected engagement records from the firm, the client evidence locker, and reviewers.";
    uses hg:hypergraph {
      refine hyperedge {
        must "not(derived-from-or-self(type, 'audit:collection')) or (count(incidence[derived-from-or-self(role, 'audit:collector')]) = 1 and count(incidence[derived-from-or-self(role, 'audit:source')]) = 1 and count(incidence[derived-from-or-self(role, 'audit:in-engagement')]) = 1 and count(incidence[derived-from-or-self(role, 'audit:collected')]) >= 1 and count(incidence) = count(incidence[derived-from-or-self(role, 'audit:collector') or derived-from-or-self(role, 'audit:source') or derived-from-or-self(role, 'audit:in-engagement') or derived-from-or-self(role, 'audit:collected')]))" {
          error-message "A collection needs one collector, one source, one engagement, at least one collected record, and no other roles.";
        }
        must "not(derived-from-or-self(type, 'audit:assessment')) or (count(incidence[derived-from-or-self(role, 'audit:assessor')]) = 1 and count(incidence[derived-from-or-self(role, 'audit:assessed-control')]) = 1 and count(incidence[derived-from-or-self(role, 'audit:in-engagement')]) = 1 and count(incidence) = count(incidence[derived-from-or-self(role, 'audit:assessor') or derived-from-or-self(role, 'audit:assessed-control') or derived-from-or-self(role, 'audit:in-engagement') or derived-from-or-self(role, 'audit:cited-evidence')]))" {
          error-message "An assessment needs one assessor, one control, one engagement, and only cited-evidence otherwise.";
        }
        must "not(derived-from-or-self(type, 'audit:assessment')) or result/outcome = 'insufficient-evidence' or count(incidence[derived-from-or-self(role, 'audit:cited-evidence')]) >= 1" {
          error-message "A supported or exception outcome must cite at least one evidence record.";
        }
        must "not(derived-from-or-self(type, 'audit:assessment')) or not(../node[id = current()/incidence[derived-from-or-self(role, 'audit:assessed-control')]/node]/control[derived-from-or-self(rule, 'audit:leaver-access')]) or (result/outcome = 'exception') = boolean(../node/account-use[breach = 'yes'])" {
          error-message "A leaver-access outcome is exception exactly when some account was used after its owner's termination.";
        }
        must "not(derived-from-or-self(type, 'audit:assessment')) or not(../node[id = current()/incidence[derived-from-or-self(role, 'audit:assessed-control')]/node]/control[derived-from-or-self(rule, 'audit:change-approval')]) or (result/outcome = 'exception') = boolean(../node/change[breach = 'yes'])" {
          error-message "A change-approval outcome is exception exactly when some privileged change lacked independent prior approval.";
        }
        must "not(derived-from-or-self(type, 'audit:assessment')) or recorded-at <= ../node[id = current()/incidence[derived-from-or-self(role, 'audit:in-engagement')]/node]/engagement/as-of" {
          error-message "An assessment cannot be recorded after the engagement's as-of time.";
        }
        must "not(derived-from-or-self(type, 'audit:review')) or (count(incidence[derived-from-or-self(role, 'audit:reviewer')]) = 1 and count(incidence[derived-from-or-self(role, 'audit:reviewed')]) = 1 and count(incidence) = 2)" {
          error-message "A review needs exactly one reviewer and one reviewed assessment.";
        }
        must "not(derived-from-or-self(type, 'audit:review')) or not(incidence[derived-from-or-self(role, 'audit:reviewer')]/node = ../hyperedge[id = current()/incidence[derived-from-or-self(role, 'audit:reviewed')]/hyperedge]/incidence[derived-from-or-self(role, 'audit:assessor')]/node)" {
          error-message "The reviewer must not be the assessor of the reviewed assessment.";
        }
        must "not(derived-from-or-self(type, 'audit:review')) or recorded-at >= ../hyperedge[id = current()/incidence[derived-from-or-self(role, 'audit:reviewed')]/hyperedge]/recorded-at" {
          error-message "A review cannot be recorded before the assessment it reviews.";
        }
        must "not(derived-from-or-self(type, 'audit:review')) or recorded-at <= ../node[id = ../hyperedge[id = current()/incidence[derived-from-or-self(role, 'audit:reviewed')]/hyperedge]/incidence[derived-from-or-self(role, 'audit:in-engagement')]/node]/engagement/as-of" {
          error-message "A review cannot be recorded after the engagement's as-of time.";
        }
        must "not(derived-from-or-self(type, 'audit:finding')) or (count(incidence[derived-from-or-self(role, 'audit:basis')]) = 1 and count(incidence[derived-from-or-self(role, 'audit:violation')]) >= 1 and count(incidence[derived-from-or-self(role, 'audit:cited-evidence')]) >= 1 and count(incidence) = count(incidence[derived-from-or-self(role, 'audit:basis') or derived-from-or-self(role, 'audit:violation') or derived-from-or-self(role, 'audit:cited-evidence')]))" {
          error-message "A finding needs one basis assessment, at least one violation, and at least one cited evidence record.";
        }
        must "not(derived-from-or-self(type, 'audit:finding')) or ../hyperedge[id = current()/incidence[derived-from-or-self(role, 'audit:basis')]/hyperedge]/result/outcome = 'exception'" {
          error-message "A finding must be based on an assessment whose outcome is exception.";
        }
        must "not(derived-from-or-self(type, 'audit:finding')) or ../hyperedge[derived-from-or-self(type, 'audit:review')][incidence[derived-from-or-self(role, 'audit:reviewed')]/hyperedge = current()/incidence[derived-from-or-self(role, 'audit:basis')]/hyperedge][sign-off/decision = 'approved']" {
          error-message "A finding's basis assessment needs an approved review.";
        }
      }
      refine hyperedge/incidence {
        must "not(derived-from-or-self(role, 'audit:collector')) or ../../node[id = current()/node][derived-from-or-self(type, 'audit:collection-agent')]" {
          error-message "A collector must be a collection-agent node.";
        }
        must "not(derived-from-or-self(role, 'audit:source')) or ../../node[id = current()/node][derived-from-or-self(type, 'audit:source-system')]" {
          error-message "A source must be a source-system node.";
        }
        must "not(derived-from-or-self(role, 'audit:collected') or derived-from-or-self(role, 'audit:cited-evidence')) or ../../node[id = current()/node][derived-from-or-self(type, 'audit:evidence-record')][not(term)]" {
          error-message "Collected and cited evidence must be evidence-record individual nodes.";
        }
        must "not(derived-from-or-self(role, 'audit:in-engagement')) or ../../node[id = current()/node][derived-from-or-self(type, 'audit:engagement')]" {
          error-message "An engagement participant must be an engagement node.";
        }
        must "not(derived-from-or-self(role, 'audit:assessor')) or ../../node[id = current()/node][derived-from-or-self(type, 'audit:practitioner') or derived-from-or-self(type, 'audit:audit-professional')]" {
          error-message "An assessor must be a practitioner or audit-professional node.";
        }
        must "not(derived-from-or-self(role, 'audit:assessed-control')) or ../../node[id = current()/node][derived-from-or-self(type, 'audit:control')][not(term)]" {
          error-message "An assessed control must be a control individual node.";
        }
        must "not(derived-from-or-self(role, 'audit:reviewer')) or ../../node[id = current()/node][derived-from-or-self(type, 'audit:audit-professional')]" {
          error-message "A reviewer must be an audit-professional node.";
        }
        must "not(derived-from-or-self(role, 'audit:reviewed') or derived-from-or-self(role, 'audit:basis')) or ../../hyperedge[id = current()/hyperedge][derived-from-or-self(type, 'audit:assessment')]" {
          error-message "Reviews and findings must reference an assessment hyperedge.";
        }
        must "not(derived-from-or-self(role, 'audit:cited-evidence')) or not(derived-from-or-self(../type, 'audit:assessment')) or ../../node[id = current()/node]/evidence-record/evidence-type = ../../node[id = current()/../incidence[derived-from-or-self(role, 'audit:assessed-control')]/node]/control/accepted-evidence" {
          error-message "Cited evidence must be of a type the assessed control accepts.";
        }
        must "not(derived-from-or-self(role, 'audit:cited-evidence')) or not(derived-from-or-self(../type, 'audit:assessment')) or ../../hyperedge[derived-from-or-self(type, 'audit:collection')][incidence[derived-from-or-self(role, 'audit:collected')]/node = current()/node][incidence[derived-from-or-self(role, 'audit:in-engagement')]/node = current()/../incidence[derived-from-or-self(role, 'audit:in-engagement')]/node]" {
          error-message "Cited evidence must come from a collection in the same engagement.";
        }
        must "not(derived-from-or-self(role, 'audit:cited-evidence')) or not(derived-from-or-self(../type, 'audit:assessment')) or ../../node[id = current()/node]/evidence-record/collected-at <= ../recorded-at" {
          error-message "Cited evidence must be collected no later than the assessment.";
        }
        must "not(derived-from-or-self(role, 'audit:cited-evidence')) or not(derived-from-or-self(../type, 'audit:assessment')) or ../../node[id = current()/node]/evidence-record/collected-at + ../../node[id = current()/../incidence[derived-from-or-self(role, 'audit:in-engagement')]/node]/engagement/max-evidence-age >= ../../node[id = current()/../incidence[derived-from-or-self(role, 'audit:in-engagement')]/node]/engagement/as-of" {
          error-message "Cited evidence is older than the engagement's maximum evidence age at its as-of time.";
        }
        must "not(derived-from-or-self(role, 'audit:violation')) or ../../node[id = current()/node]/account-use/breach = 'yes' or ../../node[id = current()/node]/change/breach = 'yes'" {
          error-message "A violation must reference a fact whose breach is yes.";
        }
        must "not(derived-from-or-self(role, 'audit:violation')) or (../../node[id = current()/node]/account-use and ../../node[id = ../hyperedge[id = current()/../incidence[derived-from-or-self(role, 'audit:basis')]/hyperedge]/incidence[derived-from-or-self(role, 'audit:assessed-control')]/node]/control[derived-from-or-self(rule, 'audit:leaver-access')]) or (../../node[id = current()/node]/change and ../../node[id = ../hyperedge[id = current()/../incidence[derived-from-or-self(role, 'audit:basis')]/hyperedge]/incidence[derived-from-or-self(role, 'audit:assessed-control')]/node]/control[derived-from-or-self(rule, 'audit:change-approval')])" {
          error-message "A violation's fact kind must match the basis control's rule.";
        }
        must "not(derived-from-or-self(role, 'audit:violation')) or ../incidence[derived-from-or-self(role, 'audit:cited-evidence')]/node = ../../node[id = current()/node]/account-use/source or ../incidence[derived-from-or-self(role, 'audit:cited-evidence')]/node = ../../node[id = current()/node]/change/source" {
          error-message "A finding must cite the evidence its violation was taken from.";
        }
      }
    }
  }

  augment "/audit:graph/audit:node" {
    description "Domain records keyed by node type, and optional term documentation.";
    uses bfo:additional-classification;
    container term {
      presence "This node documents a domain universal, not an individual.";
      description "BFO-aligned term documentation.";
      uses bfo:term-description;
    }
    container engagement {
      when "derived-from-or-self(../type, 'audit:engagement') and not(../term)";
      description "Engagement scope and reference times.";
      leaf client { type string { length "1..max"; } mandatory true; description "Fictional client name."; }
      leaf period-start { type epoch-seconds; mandatory true; description "First second of the period under review."; }
      leaf period-end {
        type epoch-seconds;
        must ". >= ../period-start" { error-message "The period cannot end before it starts."; }
        mandatory true;
        description "Last second of the period under review.";
      }
      leaf as-of {
        type epoch-seconds;
        must ". >= ../period-end" { error-message "The as-of time cannot precede the end of the period."; }
        mandatory true;
        description "Reference time of this record; evidence age is measured against it.";
      }
      leaf max-evidence-age { type uint32; units "seconds"; mandatory true; description "Oldest evidence an assessment may cite, relative to as-of."; }
    }
    container control {
      when "derived-from-or-self(../type, 'audit:control') and not(../term)";
      description "Catalogue control statement.";
      leaf reference { type string { length "1..max"; } mandatory true; description "Catalogue identifier."; }
      leaf statement { type string { length "1..max"; } mandatory true; description "Control statement."; }
      leaf rule {
        type identityref { base control-rule; }
        mandatory true;
        description "Which facts in this model decide the outcome.";
      }
      leaf-list accepted-evidence {
        type identityref { base evidence-type; }
        min-elements 1;
        description "Evidence types that can support a conclusion on this control.";
      }
    }
    container evidence-record {
      when "derived-from-or-self(../type, 'audit:evidence-record') and not(../term)";
      description "Collected artifact metadata.";
      leaf evidence-type { type identityref { base evidence-type; } mandatory true; description "Artifact kind."; }
      leaf source-system {
        type leafref { path "../../../node/id"; }
        must "../../../node[id = current()][derived-from-or-self(type, 'audit:source-system')]" {
          error-message "An evidence record's source-system must be a source-system node.";
        }
        mandatory true;
        description "Producing client system.";
      }
      leaf collected-at { type epoch-seconds; mandatory true; description "When the artifact was collected."; }
      leaf export { type string; mandatory true; description "URI reference of the exported bytes."; }
      leaf sha256 {
        type string { pattern '[0-9a-f]{64}'; }
        mandatory true;
        description "Digest of the export bytes. Byte integrity only, not truth of content.";
      }
    }
    container employee {
      when "derived-from-or-self(../type, 'audit:employee') and not(../term)";
      description "Client employee.";
      leaf staff-id { type string { length "1..max"; } mandatory true; description "HR staff identifier."; }
    }
    container account {
      when "derived-from-or-self(../type, 'audit:account') and not(../term)";
      description "Client account.";
      leaf login { type string { length "1..max"; } mandatory true; description "Account name."; }
      leaf owner {
        type leafref { path "../../../node/id"; }
        must "../../../node[id = current()][derived-from-or-self(type, 'audit:employee')]" {
          error-message "An account owner must be an employee node.";
        }
        mandatory true;
        description "Employee who owns the account.";
      }
    }
    container termination {
      when "derived-from-or-self(../type, 'audit:termination-event') and not(../term)";
      description "Termination taking effect.";
      leaf employee {
        type leafref { path "../../../node/id"; }
        must "../../../node[id = current()][derived-from-or-self(type, 'audit:employee')]" {
          error-message "A termination must reference an employee node.";
        }
        mandatory true;
        description "Terminated employee.";
      }
      leaf effective-at { type epoch-seconds; mandatory true; description "When access should end."; }
      uses fact-source;
    }
    container account-use {
      when "derived-from-or-self(../type, 'audit:account-use-event') and not(../term)";
      description "One recorded use of an account.";
      leaf account {
        type leafref { path "../../../node/id"; }
        must "../../../node[id = current()][derived-from-or-self(type, 'audit:account')]" {
          error-message "An account use must reference an account node.";
        }
        mandatory true;
        description "Account used.";
      }
      leaf at {
        type epoch-seconds;
        must "../../../node/engagement[period-start <= current() and period-end >= current()]" {
          error-message "An account use must fall within the engagement period.";
        }
        mandatory true;
        description "When the account was used.";
      }
      uses fact-source;
      leaf breach {
        type enumeration {
          enum yes { description "The owner's termination took effect before this use."; }
          enum no { description "No termination of the owner took effect before this use."; }
        }
        must "(. = 'yes') = boolean(../../../node/termination[employee = ../../node[id = current()/../account]/account/owner][effective-at < current()/../at])" {
          error-message "breach must say whether the account owner's termination took effect before this use.";
        }
        must ". = 'no' or ../../../hyperedge[derived-from-or-self(type, 'audit:finding')]/incidence[derived-from-or-self(role, 'audit:violation')]/node = current()/../../id" {
          error-message "A breach must be reported by a finding.";
        }
        mandatory true;
        description "Declared classification, checked against the termination facts.";
      }
    }
    container change {
      when "derived-from-or-self(../type, 'audit:change-event') and not(../term)";
      description "One privileged production change.";
      leaf ticket { type string { length "1..max"; } mandatory true; description "Change ticket."; }
      leaf implementer {
        type leafref { path "../../../node/id"; }
        must "../../../node[id = current()][derived-from-or-self(type, 'audit:employee')]" {
          error-message "An implementer must be an employee node.";
        }
        mandatory true;
        description "Employee who deployed the change.";
      }
      leaf approver {
        type leafref { path "../../../node/id"; }
        must "../../../node[id = current()][derived-from-or-self(type, 'audit:employee')]" {
          error-message "An approver must be an employee node.";
        }
        description "Employee who approved the change; absent when unapproved.";
      }
      leaf approved-at { when "../approver"; type epoch-seconds; mandatory true; description "When the change was approved."; }
      leaf deployed-at {
        type epoch-seconds;
        must "../../../node/engagement[period-start <= current() and period-end >= current()]" {
          error-message "A change must be deployed within the engagement period.";
        }
        mandatory true;
        description "When the change reached production.";
      }
      uses fact-source;
      leaf deployment-source {
        type leafref { path "../../../node/id"; }
        must "../../../node[id = current()][derived-from-or-self(type, 'audit:evidence-record')]" {
          error-message "A deployment source must be an evidence-record node.";
        }
        mandatory true;
        description "Evidence record the deployment time was taken from.";
      }
      leaf breach {
        type enumeration {
          enum yes { description "Unapproved, self-approved, or approved after deployment."; }
          enum no { description "Approved by someone else no later than deployment."; }
        }
        must "(. = 'yes') = boolean(not(../approver) or ../approver = ../implementer or ../approved-at > ../deployed-at)" {
          error-message "breach must say whether the change lacked independent approval before deployment.";
        }
        must ". = 'no' or ../../../hyperedge[derived-from-or-self(type, 'audit:finding')]/incidence[derived-from-or-self(role, 'audit:violation')]/node = current()/../../id" {
          error-message "A breach must be reported by a finding.";
        }
        mandatory true;
        description "Declared classification, checked against the change facts.";
      }
    }
  }

  grouping fact-source {
    description "Evidence a fact was taken from.";
    leaf source {
      type leafref { path "../../../node/id"; }
      must "../../../node[id = current()][derived-from-or-self(type, 'audit:evidence-record')]" {
        error-message "A fact's source must be an evidence-record node.";
      }
      mandatory true;
      description "Evidence record this fact was extracted from.";
    }
  }

  augment "/audit:graph/audit:hyperedge" {
    description "Engagement record details keyed by relation type.";
    leaf recorded-at {
      when "not(derived-from-or-self(../type, 'audit:workpaper-bundle'))";
      type epoch-seconds;
      mandatory true;
      description "When this record was made.";
    }
    container result {
      when "derived-from-or-self(../type, 'audit:assessment')";
      description "Assessment conclusion.";
      leaf outcome {
        type enumeration {
          enum supported { description "The facts show no breach of the control."; }
          enum exception { description "The facts show at least one breach of the control."; }
          enum insufficient-evidence { description "Evidence is not sufficient to conclude."; }
        }
        mandatory true;
        description "Conclusion on the control.";
      }
      leaf rationale { type string { length "1..max"; } mandatory true; description "Why the assessor concluded this."; }
    }
    container sign-off {
      when "derived-from-or-self(../type, 'audit:review')";
      description "Reviewer decision.";
      leaf decision {
        type enumeration {
          enum approved { description "The reviewer accepts the assessment as recorded."; }
          enum rejected { description "The reviewer sends the assessment back."; }
        }
        mandatory true;
        description "Review outcome.";
      }
      leaf comment { type string; description "Reviewer comment."; }
    }
    container detail {
      when "derived-from-or-self(../type, 'audit:finding')";
      description "Finding detail.";
      leaf severity {
        type enumeration {
          enum low { description "Low severity."; }
          enum medium { description "Medium severity."; }
          enum high { description "High severity."; }
        }
        mandatory true;
        description "Engagement team's severity rating.";
      }
      leaf condition { type string { length "1..max"; } mandatory true; description "What was found."; }
    }
  }
}
