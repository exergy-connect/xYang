module example-lab-evidence {
  yang-version 1.1;
  namespace "urn:example:lab-evidence";
  prefix ev;
  import example-lab { prefix lab; revision-date 2026-11-10; }
  organization "xYang example authors";
  contact "https://github.com/exergy-connect/xYang";
  description
    "Independent evidence-provider extension demonstrating a cross-module augment.
     SPDX-License-Identifier: MIT";
  reference "RFC 7950 section 7.17; RFC 7951 sections 4 and 6.1.";
  revision 2026-11-10 { description "Initial example revision.";
    reference "xYang examples/ontology-hypergraph/README.md"; }
  augment "/lab:graph/lab:hyperedge" {
    description "Provider review metadata; no logical entailment follows from review.";
    leaf reviewed {
      type boolean;
      description "Whether the provider reviewed this observation.";
    }
  }
}
