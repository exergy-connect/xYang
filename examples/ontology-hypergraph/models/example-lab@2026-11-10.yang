module example-lab {
  yang-version 1.1;
  namespace "urn:example:lab";
  prefix lab;
  import example-hypergraph { prefix hg; revision-date 2026-11-10; }
  import example-bfo { prefix bfo; revision-date 2026-11-10; }
  organization "xYang example authors";
  contact "https://github.com/exergy-connect/xYang";
  description
    "A laboratory ontology transport profile. Reaction hyperedges describe
     observations, not new BFO relations or a complete BFO axiomatization.
     SPDX-License-Identifier: MIT";
  reference "ISO/IEC 21838-2:2021; RFC 7950; RFC 7951.";
  revision 2026-11-10 { description "Initial example revision.";
    reference "xYang examples/ontology-hypergraph/README.md"; }

  identity specimen { base bfo:material-entity; description "Material sample examined in a laboratory."; }
  identity assay { base bfo:process; description "Process that examines a specimen."; }
  identity reaction { base hg:relation; description "N-ary reaction observation."; }
  identity bundle { base hg:relation; description "Collection of observations."; }
  identity input { base hg:role; description "Consumed or examined material."; }
  identity output { base hg:role; description "Resulting material."; }
  identity context { base hg:role; description "Optional context participant."; }
  identity member { base hg:role; description "Bundled observation."; }

  container graph {
    presence "A local graph projection is supplied.";
    description "Local projection of a distributed ontology and its instance assertions.";
    uses hg:hypergraph {
      refine hyperedge {
        must "not(derived-from-or-self(type, 'lab:reaction')) or (count(incidence[derived-from-or-self(role, 'lab:input')]) >= 1 and count(incidence[derived-from-or-self(role, 'lab:output')]) = 1 and count(incidence[not(derived-from-or-self(role, 'lab:input')) and not(derived-from-or-self(role, 'lab:output')) and not(derived-from-or-self(role, 'lab:context'))]) = 0)" {
          error-message "A reaction needs inputs, exactly one output, and only input/output/context roles.";
        }
      }
      refine hyperedge/incidence {
        must "not(derived-from-or-self(../type, 'lab:reaction')) or not(derived-from-or-self(role, 'lab:input') or derived-from-or-self(role, 'lab:output')) or ../../node[id = current()/node][not(term)][derived-from-or-self(type, 'bfo:material-entity')]" {
          error-message "Reaction inputs and outputs must reference material-entity individual nodes.";
        }
      }
    }
  }

  augment "/lab:graph/lab:node" {
    description "BFO classification and optional term documentation.";
    uses bfo:additional-classification;
    container term {
      presence "This node denotes a documented domain universal, rather than an individual.";
      description "BFO-aligned term documentation.";
      uses bfo:term-description;
    }
  }
  augment "/lab:graph/lab:hyperedge" {
    description "Domain-specific experimental record.";
    container experiment {
      when "derived-from-or-self(../type, 'lab:reaction')";
      presence "An experiment accession is supplied.";
      description "Laboratory tracking metadata.";
      leaf accession { type string { length "1..max"; } mandatory true; description "Laboratory accession."; }
    }
  }
}
