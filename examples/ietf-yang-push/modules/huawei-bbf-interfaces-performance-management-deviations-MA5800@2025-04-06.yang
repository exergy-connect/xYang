module huawei-bbf-interfaces-performance-management-deviations-MA5800 {
  namespace "urn:huawei:yang:huawei-bbf-interfaces-performance-management-deviations-MA5800";
  prefix interfaces-pm-devs;

  import ietf-interfaces {
    prefix if;
  }
  import bbf-interfaces-performance-management {
    prefix bbf-if-pm;
  }

  organization
    "Huawei Technologies Co., Ltd.";
  contact
    "Huawei Industrial Base
     Bantian, Longgang
     Shenzhen 518129
     People's Republic of China
     Website: http://www.huawei.com
     Email: support@huawei.com";
  description
    "This module defines deviation statements for bbf-interfaces-performance-management module.";

  revision 2025-04-06 {
    description
      "Initial revision.";
    reference
      "Huawei private.";
  }

  deviation "/if:interfaces/if:interface/bbf-if-pm:performance" {
    deviate not-supported;
  }
  deviation "/if:interfaces-state/if:interface/bbf-if-pm:performance" {
    deviate not-supported;
  }
}
