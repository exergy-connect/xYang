submodule huawei-gpon-gemport {
  yang-version 1;
  belongs-to huawei-xpon {
    prefix hwxpon;
  }

  import bbf-xpongemtcont {
    prefix bbf-xpongemtcont;
  }

  organization
    "Huawei Technologies Co., Ltd.";
  contact
    "Huawei Industrial Base
     Bantian, Longgang
     Shenzhen 518129
     People's Republic of China
     Website: http://www.huawei.com
     Email: support@huawei.com
     ";
  description
    "This module contains huawei extend gemport config data.";

  revision 2021-07-08 {
    description
      "Modify grouping name ex-gem-config-data and ex-gem-bundle-config-data.";
    reference
      "";
  }
  revision 2019-11-01 {
    description
      "Support GEM Port Bundle function.";
    reference
      "ITU-T G.984, G.988, G.9807, G.987, G.989";
  }
  revision 2018-04-15 {
    description
      "Initial revision.";
    reference
      "ITU-T G.984, G.988, G.9807, G.987, G.989";
  }

  grouping ex-gem-config-data {
    description
      "Config data for huawei extend GEM port.";
    leaf gem-car-traffic {
      type string {
        length "1..64";
      }
      description
        "Assigns a traffic table to a GEM port.";
    }
    leaf gem-loopback {
      type enumeration {
        enum "noloopback" {
          value 1;
          description
            "No loop back.";
        }
        enum "innerloopback" {
          value 2;
          description
            "Loop back from ONT gemport to NNI.";
        }
      }
      default "noloopback";
      description
        "Indicates the switch of GEM port loopback.";
    }
  }

  grouping ex-gem-bundle-config-data {
    description
      "Config data for huawei GEM port bundle.";
    list gem-bundle {
      key "master-gem";
      description
        "Configure a list of the GEM port bundles.";
      leaf master-gem {
        type leafref {
          path "/bbf-xpongemtcont:xpongemtcont/bbf-xpongemtcont:gemports/bbf-xpongemtcont:gemport/bbf-xpongemtcont:name";
        }
        description
          "Indicates the master GEM port of bundle.";
      }
      container slave-gem {
        description
          "Configure the slave GEM ports of bundle.";
        leaf-list slave-gem {
          type leafref {
            path "/bbf-xpongemtcont:xpongemtcont/bbf-xpongemtcont:gemports/bbf-xpongemtcont:gemport/bbf-xpongemtcont:name";
          }
          max-elements 7;
          description
            "Configure a list of slave GEM port.";
        }
      }
    }
  }
}
