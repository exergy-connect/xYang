submodule huawei-srpolicy-type {
  belongs-to huawei-srpolicy {
    prefix srpolicy;
  }

  import ietf-inet-types {
    prefix inet;
  }

  organization
    "Huawei Technologies Co., Ltd.";
  contact
    "Huawei Industrial Base
     Bantian, Longgang
     Shenzhen 518129
     People's Republic of China
     Website: http://www.huawei.com
     Email: support@huawei.com";
  description
    "Segment-routing type defined file.";

  revision 2025-05-27 {
    description
      "Added dual-fed-type, and group-create-type.";
    reference
      "Huawei private.";
  }
  revision 2024-10-28 {
    description
      "Added path-mtu-detect-type, group-match-type, service-class-type, binding-sid-endpoint-behavior-type, map-match-type, address-family-display-type, and path-mtu-detected-state-type.";
    reference
      "Huawei private.";
  }
  revision 2024-09-01 {
    description
      "Added xsid-encapsulation-type.";
    reference
      "Huawei private.";
  }
  revision 2023-11-20 {
    description
      "The enumerated value no-flavor is deleted from compress-flavor-type.";
    reference
      "Huawei private.";
  }
  revision 2023-03-08 {
    description
      "Add the enumerated values of bfd-bypass-type and policy-bfd-bypass-type.";
    reference
      "Huawei private.";
  }
  revision 2023-02-28 {
    description
      "Add shortcut-mode.";
    reference
      "Huawei private.";
  }
  revision 2023-02-25 {
    description
      "Add sid-selection-type.";
    reference
      "Huawei private.";
  }
  revision 2022-11-08 {
    description
      "Add the enumerated value of compress-flavor-type.";
    reference
      "Huawei private.";
  }
  revision 2022-10-24 {
    description
      "Add policy-compute-type.";
    reference
      "Huawei private.";
  }
  revision 2022-10-12 {
    description
      "Add metric-type, hop-type, constraint-type, affinity-include-type, global-compute-type, delegate-protocol-type.";
    reference
      "Huawei private.";
  }
  revision 2022-04-15 {
    description
      "Add ifit-measure-mode-type.";
    reference
      "Huawei private.";
  }
  revision 2022-03-08 {
    description
      "Increate the function to specify the return tunnel of seamless BFD packets based on a specified binding SID.";
    reference
      "Huawei private.";
  }
  revision 2020-09-14 {
    description
      "Increate the BFD bypass type and policy BFD bypass type.";
    reference
      "Huawei private.";
  }
  revision 2020-06-28 {
    description
      "Modify description information.";
    reference
      "Huawei private.";
  }
  revision 2020-06-20 {
    description
      "Increate the template-enable-type.";
    reference
      "Huawei private.";
  }
  revision 2020-06-01 {
    description
      "Increate the path verification.";
    reference
      "Huawei private.";
  }
  revision 2020-05-25 {
    description
      "Increate the group-state-type.";
    reference
      "Huawei private.";
  }
  revision 2020-05-20 {
    description
      "Increate the admin-state-type.";
    reference
      "Huawei private.";
  }
  revision 2020-03-26 {
    description
      "Modify description by new rules.";
    reference
      "Huawei private.";
  }
  revision 2020-03-16 {
    description
      "Modify description by new rules.";
    reference
      "Huawei private.";
  }
  revision 2019-11-18 {
    description
      "Increate the SR-MPLS TE Policy group.";
    reference
      "Huawei private.";
  }
  revision 2019-04-04 {
    description
      "Initial revision.";
    reference
      "Huawei private.";
  }

  typedef bfd-enable-type {
    type enumeration {
      enum "disable" {
        value 0;
        description
          "Disable.";
      }
      enum "sbfd-enable" {
        value 1;
        description
          "SBFD enable.";
      }
      enum "ubfd-enable" {
        value 2;
        description
          "Unaffiliated BFD enable.";
      }
      enum "ubfd-enable-reverse-path-bsid" {
        value 3;
        description
          "Enable the function to specify the return tunnel of unaffiliated BFD packets based on a specified binding SID.";
      }
      enum "sbfd-enable-reverse-path-bsid" {
        value 4;
        description
          "Enable the function to specify the return tunnel of seamless BFD packets based on a specified binding SID.";
      }
      enum "ubfd-enable-reverse-path-xsid" {
        value 5;
        description
          "Enable the function to specify the return tunnel of unaffiliated BFD packets based on a specified XSID.";
      }
    }
    description
      "BFD enable type.";
  }

  typedef bfd-bypass-type {
    type enumeration {
      enum "bypass" {
        value 0;
        description
          "BFD bypass enable.";
      }
      enum "nobypass" {
        value 1;
        description
          "BFD nobypass enable.";
      }
      enum "nobypass-preferred" {
        value 2;
        description
          "BFD nobypass preferred enable.";
      }
    }
    description
      "BFD bypass enable type.";
  }

  typedef dataplane-type {
    type enumeration {
      enum "mpls" {
        value 1;
        description
          "Segment-routing MPLS.";
      }
      enum "srv6" {
        value 2;
        description
          "Segment-routing IPv6.";
      }
    }
    description
      "Dataplane type of the segments.";
  }

  typedef sid-value-type {
    type union {
      type uint32 {
        range "16..1048575";
      }
      type inet:ipv6-address-no-zone;
    }
    description
      "The sid value type.";
  }

  typedef path-type {
    type enumeration {
      enum "primary" {
        value 1;
        description
          "Primary path.";
      }
      enum "backup" {
        value 2;
        description
          "Backup path.";
      }
      enum "no-active" {
        value 3;
        description
          "No active path.";
      }
    }
    description
      "Path type.";
  }

  typedef protocol-origin-type {
    type enumeration {
      enum "pcep" {
        value 10;
        description
          "PCEP config.";
      }
      enum "bgp" {
        value 20;
        description
          "BGP config.";
      }
      enum "configuration" {
        value 30;
        description
          "Manual config.";
      }
    }
    description
      "Protocol origin type.";
  }

  typedef policy-bfd-enable-type {
    type enumeration {
      enum "not-configured" {
        value 0;
        description
          "Not configured.";
      }
      enum "sbfd-enable" {
        value 1;
        description
          "SBFD enable.";
      }
      enum "disable" {
        value 2;
        description
          "Disable.";
      }
      enum "ubfd-enable" {
        value 3;
        description
          "Unaffiliated BFD enable.";
      }
      enum "ubfd-enable-reverse-path-bsid" {
        value 4;
        description
          "Enable the function to specify the return tunnel of unaffiliated BFD packets based on a specified binding SID.";
      }
      enum "sbfd-enable-reverse-path-bsid" {
        value 5;
        description
          "Enable the function to specify the return tunnel of seamless BFD packets based on a specified binding SID.";
      }
      enum "ubfd-enable-reverse-path-xsid" {
        value 6;
        description
          "Enable the function to specify the return tunnel of unaffiliated BFD packets based on a specified XSID.";
      }
    }
    description
      "BFD enable type for SR Policy.";
  }

  typedef policy-bfd-bypass-type {
    type enumeration {
      enum "not-configured" {
        value 0;
        description
          "Not configured.";
      }
      enum "bfd-bypass" {
        value 1;
        description
          "BFD bypass enable.";
      }
      enum "bfd-nobypass" {
        value 2;
        description
          "BFD nobypass enable.";
      }
      enum "bfd-nobypass-preferred" {
        value 3;
        description
          "BFD nobypass preferred enable.";
      }
    }
    description
      "BFD bypass type for SR policy.";
  }

  typedef enable-3types {
    type enumeration {
      enum "not-configured" {
        value 0;
        description
          "Not configured.";
      }
      enum "enable" {
        value 1;
        description
          "Enable.";
      }
      enum "disable" {
        value 2;
        description
          "Disable.";
      }
    }
    description
      "Enable 3 types.";
  }

  typedef pipe-mode-type {
    type enumeration {
      enum "pipe" {
        value 1;
        description
          "Pipe Mode.";
      }
      enum "uniform" {
        value 2;
        description
          "Uniform Mode.";
      }
    }
    description
      "Pipe mode types.";
  }

  typedef serv-class-disp-types {
    type enumeration {
      enum "be" {
        value 0;
        description
          "BE service-class.";
      }
      enum "af1" {
        value 1;
        description
          "AF1 service-class.";
      }
      enum "af2" {
        value 2;
        description
          "AF2 service-class.";
      }
      enum "af3" {
        value 3;
        description
          "AF3 service-class.";
      }
      enum "af4" {
        value 4;
        description
          "AF4 service-class.";
      }
      enum "ef" {
        value 5;
        description
          "EF service-class.";
      }
      enum "cs6" {
        value 6;
        description
          "CS6 service-class.";
      }
      enum "cs7" {
        value 7;
        description
          "CS7 service-class.";
      }
      enum "none" {
        value 8;
        description
          "None service-class.";
      }
    }
    description
      "Service class types.";
  }

  typedef serv-color-disp-types {
    type enumeration {
      enum "green" {
        value 0;
        description
          "Green.";
      }
      enum "yellow" {
        value 1;
        description
          "Yellow.";
      }
      enum "red" {
        value 2;
        description
          "Red.";
      }
      enum "none" {
        value 3;
        description
          "None service-color.";
      }
    }
    description
      "Service color types.";
  }

  typedef serv-class-types {
    type enumeration {
      enum "be" {
        value 0;
        description
          "BE service-class.";
      }
      enum "af1" {
        value 1;
        description
          "AF1 service-class.";
      }
      enum "af2" {
        value 2;
        description
          "AF2 service-class.";
      }
      enum "af3" {
        value 3;
        description
          "AF3 service-class.";
      }
      enum "af4" {
        value 4;
        description
          "AF4 service-class.";
      }
      enum "ef" {
        value 5;
        description
          "EF service-class.";
      }
      enum "cs6" {
        value 6;
        description
          "CS6 service-class.";
      }
      enum "cs7" {
        value 7;
        description
          "CS7 service-class.";
      }
    }
    description
      "Service class types.";
  }

  typedef serv-color-types {
    type enumeration {
      enum "green" {
        value 0;
        description
          "Green.";
      }
      enum "yellow" {
        value 1;
        description
          "Yellow.";
      }
      enum "red" {
        value 2;
        description
          "Red.";
      }
    }
    description
      "Service color types.";
  }

  typedef address-family-type {
    type enumeration {
      enum "ipv4" {
        value 4;
        description
          "IPv4.";
      }
      enum "ipv6" {
        value 6;
        description
          "IPv6.";
      }
    }
    description
      "Address family type.";
  }

  typedef segment-type {
    type enumeration {
      enum "segment-type-1" {
        value 1;
        description
          "SR-MPLS label.";
      }
      enum "segment-type-2" {
        value 2;
        description
          "SRv6 sid.";
      }
      enum "segment-type-3" {
        value 3;
        description
          "IPv4 Prefix with optional SR Algorithm.";
      }
      enum "segment-type-4" {
        value 4;
        description
          "IPv6 Global Prefix with optional SR Algorithm for SR-MPLS.";
      }
      enum "segment-type-5" {
        value 5;
        description
          "IPv4 Prefix with Local Interface ID.";
      }
      enum "segment-type-6" {
        value 6;
        description
          "IPv4 Addresses for link endpoints as Local, Remote pair.";
      }
      enum "segment-type-7" {
        value 7;
        description
          "IPv6 Prefix and Interface ID for link endpoints as Local, Remote pair for SR-MPLS.";
      }
      enum "segment-type-8" {
        value 8;
        description
          "IPv6 Addresses for link endpoints as Local, Remote pair for SR-MPLS.";
      }
      enum "segment-type-9" {
        value 9;
        description
          "IPv6 Global Prefix with optional SR Algorithm for SRv6.";
      }
      enum "segment-type-10" {
        value 10;
        description
          "IPv6 Prefix and Interface ID for link endpoints as Local, Remote pair for SRv6.";
      }
      enum "segment-type-11" {
        value 11;
        description
          "IPv6 Addresses for link endpoints as Local, Remote pair for SRv6.";
      }
    }
    description
      "SR segment type.";
  }

  typedef path-state-type {
    type enumeration {
      enum "invalid" {
        value 0;
        description
          "Invalid.";
      }
      enum "valid" {
        value 1;
        description
          "Valid.";
      }
    }
    description
      "Policy candidate-path state.";
  }

  typedef enable-type {
    type enumeration {
      enum "enable" {
        value 1;
        description
          "Enable.";
      }
      enum "disable" {
        value 0;
        description
          "Disable.";
      }
    }
    description
      "Enable types.";
  }

  typedef tunnel-type {
    type enumeration {
      enum "SRV6-TE-POLICY-GROUP" {
        value 55;
        description
          "SRv6 TE Policy group.";
      }
      enum "SRV6-TE-POLICY" {
        value 52;
        description
          "SRV6.";
      }
      enum "SR-MPLS-TE-POLICY-GROUP" {
        value 51;
        description
          "SR group.";
      }
      enum "SR-MPLS-TE-POLICY" {
        value 50;
        description
          "SR.";
      }
      enum "INVALID" {
        value 0;
        description
          "Invalid.";
      }
    }
    description
      "SR Policy tunnel types.";
  }

  typedef policy-state-type {
    type enumeration {
      enum "active" {
        value 1;
        description
          "Active.";
      }
      enum "deactive" {
        value 2;
        description
          "Deactive.";
      }
    }
    description
      "Policy state types.";
  }

  typedef state-type {
    type enumeration {
      enum "up" {
        value 0;
        description
          "Up.";
      }
      enum "down" {
        value 1;
        description
          "Down.";
      }
      enum "overrun" {
        value 2;
        description
          "OverRun.";
      }
    }
    description
      "SR Policy state.";
  }

  typedef admin-state-type {
    type enumeration {
      enum "down" {
        value 0;
        description
          "Administrative status is down.";
      }
      enum "up" {
        value 1;
        description
          "Administrative status is up.";
      }
    }
    description
      "SR Policy admin state.";
  }

  typedef flow-priority-type {
    type enumeration {
      enum "dscp" {
        value 0;
        description
          "DSCP.";
      }
    }
    description
      "Traffic priority types.";
  }

  typedef dscp-type {
    type string {
      length "1..64";
      pattern "((6[0-3]|[1-5][0-9]|[0-9])(-(6[0-3]|[1-5][0-9]|[0-9]))?(,((6[0-3]|[1-5][0-9]|[0-9])(-(6[0-3]|[1-5][0-9]|[0-9]))?))*)|default";
    }
    description
      "Type definition for DSCP value.";
  }

  typedef group-state-type {
    type enumeration {
      enum "down" {
        value 0;
        description
          "Down.";
      }
      enum "up" {
        value 1;
        description
          "Up.";
      }
      enum "delay-delete" {
        value 2;
        description
          "Delay delete.";
      }
    }
    description
      "SR Policy group state.";
  }

  typedef group-down-reason-type {
    type enumeration {
      enum "none" {
        value 0;
        description
          "None.";
      }
      enum "no-active-sr-policy" {
        value 1;
        description
          "No active SR Policy exists.";
      }
      enum "subscribe-delete" {
        value 2;
        description
          "SR Policy group subscription is deleted.";
      }
      enum "configuration-delete" {
        value 3;
        description
          "Configuration delete.";
      }
      enum "unknown-reason" {
        value 4;
        description
          "Unknown reason.";
      }
    }
    description
      "SR Policy group down reason types.";
  }

  typedef map-down-reason-type {
    type enumeration {
      enum "none" {
        value 0;
        description
          "None.";
      }
      enum "sr-policy-down" {
        value 1;
        description
          "SR Policy down.";
      }
      enum "configuration-delete" {
        value 2;
        description
          "Mapping policy configuration is deleted.";
      }
      enum "sr-policy-group-delete" {
        value 3;
        description
          "The SR Policy group is deleted.";
      }
      enum "unknown-reason" {
        value 4;
        description
          "Unknown reason.";
      }
    }
    description
      "Mappings down reason types.";
  }

  typedef protocol-type {
    type enumeration {
      enum "isis" {
        value 1;
        description
          "ISIS.";
      }
    }
    description
      "The protocol type.";
  }

  typedef function-type {
    type enumeration {
      enum "end" {
        value 1;
        description
          "End type.";
      }
      enum "end-x" {
        value 4;
        description
          "End.X type.";
      }
    }
    description
      "The sid type.";
  }

  typedef level-type {
    type enumeration {
      enum "level-1" {
        value 1;
        description
          "Level 1.";
      }
      enum "level-2" {
        value 2;
        description
          "Level 2.";
      }
    }
    description
      "The level type.";
  }

  typedef sub-process-type {
    type union {
      type level-type;
    }
    description
      "The sub process type.";
  }

  typedef template-enable-type {
    type enumeration {
      enum "enable" {
        value 1;
        description
          "Enable type.";
      }
      enum "disable" {
        value 2;
        description
          "Disable type.";
      }
    }
    description
      "Template enable types.";
  }

  typedef encapsulation-cfg-type {
    type enumeration {
      enum "insert" {
        value 1;
        description
          "Insert encapsulation mode.";
      }
      enum "encaps" {
        value 2;
        description
          "Encaps encapsulation mode.";
      }
      enum "insert-encaps" {
        value 3;
        description
          "Insert and encaps encapsulation mode.";
      }
    }
    description
      "Encapsulation modes.";
  }

  typedef encapsulation-disp-type {
    type enumeration {
      enum "invalid" {
        value 0;
        description
          "Invalid encapsulation mode.";
      }
      enum "insert" {
        value 1;
        description
          "Insert encapsulation mode.";
      }
      enum "encaps" {
        value 2;
        description
          "Encaps encapsulation mode.";
      }
      enum "insert-encaps" {
        value 3;
        description
          "Insert and encaps encapsulation mode.";
      }
    }
    description
      "Encapsulation modes.";
  }

  typedef global-path-verification-type {
    type enumeration {
      enum "disable" {
        value 0;
        description
          "Verification disable.";
      }
      enum "enable" {
        value 1;
        description
          "Verification enable.";
      }
      enum "specified-sid-enable" {
        value 2;
        description
          "Specified verification enable.";
      }
    }
    description
      "Global path verification enable types.";
  }

  typedef path-verification-type {
    type enumeration {
      enum "not-configured" {
        value 0;
        description
          "Not configured.";
      }
      enum "enable" {
        value 1;
        description
          "Verification enable.";
      }
      enum "disable" {
        value 2;
        description
          "Verification disable.";
      }
      enum "specified-sid-enable" {
        value 3;
        description
          "Specified verification enable.";
      }
    }
    description
      "Path verification enable types.";
  }

  typedef policy-fwd-no-bypass-type {
    type enumeration {
      enum "no-bypass" {
        value 1;
        description
          "Forward no-bypass enable.";
      }
    }
    description
      "Forward no-bypass enable types.";
  }

  typedef sla-type {
    type enumeration {
      enum "one-way-delay" {
        value 0;
        description
          "One-way delay.";
      }
      enum "two-way-delay" {
        value 1;
        description
          "Two-way delay.";
      }
      enum "one-way-jitter" {
        value 2;
        description
          "One-way jitter.";
      }
      enum "two-way-jitter" {
        value 3;
        description
          "Two-way jitter.";
      }
      enum "one-way-loss" {
        value 4;
        description
          "One-way loss-rate.";
      }
      enum "two-way-loss" {
        value 5;
        description
          "Two-way loss-rate.";
      }
    }
    description
      "SR Policy SLA types.";
  }

  typedef ifit-measure-mode-type {
    type enumeration {
      enum "e2e" {
        value 3;
        description
          "IFIT measure mode E2E.";
      }
      enum "trace" {
        value 4;
        description
          "IFIT measure mode TRACE.";
      }
    }
    description
      "SR Policy IFIT measure mode.";
  }

  typedef metric-type {
    type enumeration {
      enum "igp" {
        value 1;
        description
          "IGP metric.";
      }
      enum "te" {
        value 2;
        description
          "TE metric.";
      }
      enum "delay" {
        value 3;
        description
          "Delay metric.";
      }
      enum "hop-count" {
        value 4;
        description
          "Number of hops.";
      }
    }
    description
      "Metric type.";
  }

  typedef hop-type {
    type enumeration {
      enum "ipv4-address" {
        value 1;
        description
          "IPv4 address.";
      }
    }
    description
      "SR hop type.";
  }

  typedef constraint-type {
    type enumeration {
      enum "include-strict" {
        value 1;
        description
          "Strictly include the specified address.";
      }
      enum "include-loose" {
        value 2;
        description
          "Loosely include the specified address.";
      }
      enum "exclude" {
        value 3;
        description
          "Exclude any specified address.";
      }
    }
    description
      "Hop constraint type.";
  }

  typedef affinity-include-type {
    type enumeration {
      enum "include-all" {
        value 1;
        description
          "Include all specified administrative groups.";
      }
      enum "include-any" {
        value 2;
        description
          "Include any specified administrative group.";
      }
      enum "exclude" {
        value 3;
        description
          "Exclude any specified administrative group.";
      }
    }
    description
      "Affinity inclusion type.";
  }

  typedef global-compute-type {
    type enumeration {
      enum "pcep" {
        value 1;
        description
          "PCEP.";
      }
      enum "local" {
        value 2;
        description
          "Local.";
      }
    }
    description
      "Global computation source type.";
  }

  typedef delegate-protocol-type {
    type enumeration {
      enum "none" {
        value 0;
        description
          "None.";
      }
      enum "pcep" {
        value 1;
        description
          "PCEP.";
      }
      enum "local" {
        value 3;
        description
          "Local.";
      }
    }
    description
      "Type of the delegation protocol.";
  }

  typedef policy-compute-type {
    type enumeration {
      enum "pcep" {
        value 1;
        description
          "PCEP.";
      }
      enum "none" {
        value 2;
        description
          "None.";
      }
      enum "local" {
        value 3;
        description
          "Local.";
      }
    }
    description
      "SR Policy specific computation source type.";
  }

  typedef compress-flavor-type {
    type enumeration {
      enum "coc-next" {
        value 1;
        description
          "Replacement and shift are both supported.";
      }
      enum "coc" {
        value 2;
        description
          "Only the replacement is supported.";
      }
      enum "next" {
        value 3;
        description
          "Only the shift is supported.";
      }
    }
    description
      "Flavor of a 16-bit compressed SID.";
  }

  typedef sid-selection-type {
    type enumeration {
      enum "unprotected-preferred" {
        value 0;
        description
          "Unprotected SIDs are preferred.";
      }
      enum "protected-preferred" {
        value 1;
        description
          "Protected SIDs are preferred.";
      }
      enum "unprotected-only" {
        value 2;
        description
          "Only unprotected SIDs can be used.";
      }
      enum "protected-only" {
        value 3;
        description
          "Only protected SIDs can be used.";
      }
    }
    description
      "SID selection type.";
  }

  typedef shortcut-mode {
    type enumeration {
      enum "disable" {
        value 0;
        description
          "Disable IGP shortcut.";
      }
      enum "isis" {
        value 1;
        description
          "ISIS.";
      }
    }
    description
      "IGP shortcut type.";
  }

  typedef global-inherit-mode {
    type enumeration {
      enum "igp" {
        value 1;
        description
          "Metric inheritance from IGP.";
      }
      enum "te" {
        value 2;
        description
          "Metric inheritance from TE.";
      }
      enum "delay" {
        value 3;
        description
          "Metric inheritance from delay.";
      }
    }
    description
      "Global metric inheritance mode.";
  }

  typedef metric-inherit-mode {
    type enumeration {
      enum "igp" {
        value 1;
        description
          "Metric inheritance from IGP.";
      }
      enum "te" {
        value 2;
        description
          "Metric inheritance from TE.";
      }
      enum "delay" {
        value 3;
        description
          "Metric inheritance from delay.";
      }
      enum "disable" {
        value 255;
        description
          "Disable metric inheritance.";
      }
    }
    description
      "Metric inheritance mode.";
  }

  typedef metric-value-type {
    type enumeration {
      enum "te" {
        value 2;
        description
          "TE metric.";
      }
      enum "delay" {
        value 3;
        description
          "Delay metric.";
      }
    }
    description
      "Metric type in policy.";
  }

  typedef path-computation-mode-type {
    type enumeration {
      enum "sid-filter" {
        value 0;
        description
          "SID filter.";
      }
      enum "flex-algo" {
        value 1;
        description
          "Flexible Algorithm.";
      }
    }
    description
      "Path computation mode type.";
  }

  typedef bfd-slice-inherit-match-type {
    type enumeration {
      enum "source-prefix" {
        value 1;
        description
          "Source prefix.";
      }
      enum "inherit" {
        value 2;
        description
          "Inherit.";
      }
      enum "disable" {
        value 3;
        description
          "Disable.";
      }
    }
    description
      "Inheritance type (for the network slice's match mode) of BFD detection packets configured for the SRv6 TE Policy.";
  }

  typedef metric-source-mode {
    type enumeration {
      enum "route" {
        value 1;
        description
          "Metric from route.";
      }
      enum "bgp" {
        value 2;
        description
          "Metric from BGP.";
      }
      enum "pcep" {
        value 3;
        description
          "Metric from PCEP.";
      }
      enum "cfg" {
        value 4;
        description
          "Metric from configuration.";
      }
    }
    description
      "Metric source in SR Policy.";
  }

  typedef disjointness-type {
    type enumeration {
      enum "link" {
        value 1;
        description
          "Link disjointness.";
      }
      enum "node" {
        value 2;
        description
          "Node disjointness.";
      }
      enum "srlg" {
        value 4;
        description
          "SRLG disjointness.";
      }
      enum "srlg-node" {
        value 6;
        description
          "SRLG and node disjointness.";
      }
    }
    description
      "Disjointness type.";
  }

  typedef of-code {
    type enumeration {
      enum "msl" {
        value 1;
        description
          "Minimize the number of shared links.";
      }
      enum "mss" {
        value 2;
        description
          "Minimize the number of shared SRLGs.";
      }
      enum "msn" {
        value 3;
        description
          "Minimize the number of shared nodes.";
      }
    }
    description
      "Objective function code.";
  }

  typedef template-bfd-slice-inherit-type {
    type enumeration {
      enum "inherit" {
        value 2;
        description
          "Inherit.";
      }
      enum "disable" {
        value 3;
        description
          "Disable.";
      }
    }
    description
      "Inheritance type (for the network slice's match mode) of BFD detection packets configured for the SR Policy template.";
  }

  typedef bfd-slice-inherit-match-disp-type {
    type enumeration {
      enum "disable" {
        value 0;
        description
          "Disable.";
      }
      enum "source-prefix" {
        value 1;
        description
          "Source prefix.";
      }
      enum "inherit" {
        value 2;
        description
          "Inherit.";
      }
    }
    description
      "Display the active inheritance type for the SRv6 TE Policy.";
  }

  typedef constraint-path-hop-type {
    type enumeration {
      enum "ipv4" {
        value 0;
        description
          "IPv4 address.";
      }
      enum "ipv6" {
        value 1;
        description
          "IPv6 address.";
      }
    }
    description
      "Constraint path hop type.";
  }

  typedef xsid-encapsulation-type {
    type enumeration {
      enum "encaps" {
        value 2;
        description
          "Encaps encapsulation mode.";
      }
    }
    description
      "XSID encapsulation modes.";
  }

  typedef path-mtu-detect-type {
    type enumeration {
      enum "disable" {
        value 1;
        description
          "Disable.";
      }
      enum "detect-only" {
        value 2;
        description
          "Detect.";
      }
      enum "forward-update" {
        value 3;
        description
          "Forward update.";
      }
    }
    description
      "Path MTU detection type.";
  }

  typedef delete-hold-type {
    type enumeration {
      enum "disable" {
        value 0;
        description
          "Disable.";
      }
      enum "enable" {
        value 1;
        description
          "Enable.";
      }
    }
    description
      "Delete Hold type.";
  }

  typedef bsid-endpoint-behavior-type {
    type enumeration {
      enum "encaps" {
        value 1;
        description
          "Encaps.";
      }
      enum "insert" {
        value 2;
        description
          "Insert.";
      }
      enum "encaps-reduce" {
        value 3;
        description
          "Encaps-reduce.";
      }
      enum "insert-reduce" {
        value 4;
        description
          "Insert-reduce.";
      }
    }
    description
      "Binding SID endpoint behavior.";
  }

  typedef group-match-type {
    type bits {
      bit dscp {
        position 0;
        description
          "DSCP.";
      }
      bit service-class {
        position 3;
        description
          "Service Class.";
      }
    }
    description
      "Group match type.";
  }

  typedef service-class-type {
    type bits {
      bit be {
        position 0;
        description
          "Service name is BE.";
      }
      bit af1 {
        position 1;
        description
          "Service name is AF1.";
      }
      bit af2 {
        position 2;
        description
          "Service name is AF2.";
      }
      bit af3 {
        position 3;
        description
          "Service name is AF3.";
      }
      bit af4 {
        position 4;
        description
          "Service name is AF4.";
      }
      bit ef {
        position 5;
        description
          "Service name is EF.";
      }
      bit cs6 {
        position 6;
        description
          "Service name is CS6.";
      }
      bit cs7 {
        position 7;
        description
          "Service name is CS7.";
      }
    }
    description
      "Service Class type.";
  }

  typedef map-match-type {
    type enumeration {
      enum "dscp" {
        value 0;
        description
          "DSCP.";
      }
      enum "service-class" {
        value 3;
        description
          "Service Class.";
      }
    }
    description
      "Group mapping match type.";
  }

  typedef policy-group-down-reason-type {
    type enumeration {
      enum "no-active-tunnel" {
        value 1;
        description
          "No active tunnel exists.";
      }
      enum "subscribe-delete" {
        value 2;
        description
          "Subscription information is deleted.";
      }
      enum "configuration-delete" {
        value 3;
        description
          "Configuration is deleted.";
      }
      enum "unknown-reason" {
        value 4;
        description
          "Unknown reason.";
      }
      enum "no-endpoint" {
        value 5;
        description
          "Endpoint is deleted.";
      }
    }
    description
      "Types of SR-MPLS TE Policy group down reasons.";
  }

  typedef address-family-display-type {
    type enumeration {
      enum "ipv4-ipv6" {
        value 1;
        description
          "IPv4 and IPv6.";
      }
      enum "ipv4" {
        value 4;
        description
          "IPv4.";
      }
      enum "ipv6" {
        value 6;
        description
          "IPv6.";
      }
    }
    description
      "Address family type.";
  }

  typedef afr-type {
    type enumeration {
      enum "enable" {
        value 1;
        description
          "Enable.";
      }
    }
    description
      "Type of adaptive flow repathing.";
  }

  typedef path-mtu-detected-state-type {
    type enumeration {
      enum "pass" {
        value 0;
        description
          "Passed.";
      }
      enum "timeout" {
        value 1;
        description
          "Timeout.";
      }
      enum "fail" {
        value 2;
        description
          "Failed.";
      }
      enum "issu-upgrade" {
        value 3;
        description
          "ISSU upgrade.";
      }
      enum "unknown" {
        value 4;
        description
          "Unknown.";
      }
    }
    description
      "Path MTU detection state.";
  }

  typedef dual-fed-type {
    type enumeration {
      enum "disable" {
        value 0;
        description
          "Disable.";
      }
      enum "enable" {
        value 1;
        description
          "Enable.";
      }
    }
    description
      "Dual-fed type.";
  }

  typedef group-create-type {
    type enumeration {
      enum "dynamic" {
        value 0;
        description
          "The create type is dynamic.";
      }
      enum "static" {
        value 1;
        description
          "The create type is static.";
      }
    }
    description
      "Create type of an SR-MPLS TE Policy group.";
  }
}
