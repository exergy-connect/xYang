module huawei-bgp-evpn {
  namespace "urn:huawei:yang:huawei-bgp-evpn";
  prefix bgp-evpn;

  import huawei-network-instance {
    prefix ni;
  }
  import huawei-bgp {
    prefix bgp;
  }
  import huawei-routing-policy {
    prefix rtp;
  }
  import huawei-bgp-routing-table {
    prefix bgp-rt;
  }
  import huawei-extension {
    prefix ext;
  }
  import ietf-inet-types {
    prefix inet;
  }
  import huawei-xpl {
    prefix xpl;
  }
  import huawei-l3vpn {
    prefix l3vpn;
  }

  organization
    "Huawei Technologies Co., Ltd.";
  contact
    "Huawei Industrial Base
     Bantian, Longgang
     Shenzhen 518129
     People's Republic of China
     Website: http://www.huawei.com
     Email: support@huawei.com";
  description
    "Configure BGP EVPN.";

  revision 2025-11-20 {
    description
      "Add container default-route-originates.";
    reference
      "Huawei private.";
  }
  revision 2024-09-03 {
    description
      "Modify route type field of ad-route info.";
    reference
      "Huawei private.";
  }
  revision 2024-01-11 {
    description
      "Delete when condition of reflect-client.";
    reference
      "Huawei private.";
  }
  revision 2023-12-19 {
    description
      "Modify the when condition of container remote-crosss.";
    reference
      "Huawei private.";
  }
  revision 2023-11-21 {
    description
      "Modify the description of single-group-detection-threshold.";
    reference
      "Huawei private.";
  }
  revision 2023-11-02 {
    description
      "Add leaf node of slow-peer. Add advertise-ip-esad leaf and xsec leaf. Add container remote-crosss. Add rekey-counter. Add srv6-label-compatible2 leaf and srv6-inclusive-label-compatible2 leaf.";
    reference
      "Huawei private.";
  }
  revision 2023-09-22 {
    description
      "Add unique-source-ip-prefix node.";
    reference
      "Huawei private.";
  }
  revision 2023-08-18 {
    description
      "Add inclusive-route-pmsi-compatible node.";
    reference
      "Huawei private.";
  }
  revision 2023-07-24 {
    description
      "Add vpn-orf-enhance-advertise node.";
    reference
      "Huawei private.";
  }
  revision 2023-07-14 {
    description
      "Add policy-type node.";
    reference
      "Huawei private.";
  }
  revision 2023-04-25 {
    description
      "Modify description of color-only.";
    reference
      "Huawei private.";
  }
  revision 2023-04-13 {
    description
      "Modify routing table attribute behavior datatype from uint16 to character string (1..32).";
    reference
      "Huawei private.";
  }
  revision 2023-03-22 {
    description
      "Modify routing table attribute behavior datatype from uint16 to character string (1..32).";
    reference
      "Huawei private.";
  }
  revision 2023-03-16 {
    description
      "Add color-only node.";
    reference
      "Huawei private.";
  }
  revision 2023-02-09 {
    description
      "Add the slow-delete sids rpc node.";
    reference
      "Huawei private.";
  }
  revision 2022-10-19 {
    description
      "Add must condition peer-establish-mode='static' for instance-process leaf group-name.";
    reference
      "Huawei private.";
  }
  revision 2022-09-20 {
    description
      "Add option-group container.";
    reference
      "Huawei private.";
  }
  revision 2022-06-30 {
    description
      "Add interworking-related nodes. Add original-attributes nodes.";
    reference
      "Huawei private.";
  }
  revision 2022-03-09 {
    description
      "Add option container.";
    reference
      "Huawei private.";
  }
  revision 2021-08-06 {
    description
      "Update EVPN module YANG file for BGP EVPN peer.";
    reference
      "Huawei private.";
  }
  revision 2020-04-07 {
    description
      "EVPN module YANG file.";
    reference
      "Huawei private.";
  }
  revision 2019-03-22 {
    description
      "Initial revision.";
    reference
      "Huawei private.";
  }

 

  typedef advertise-encap-type {
    type enumeration {
      enum "vxlan" {
        value 1;
        description
          "VXLAN.";
      }
      enum "mpls" {
        value 2;
        description
          "MPLS.";
      }
      enum "srv6" {
        value 4;
        description
          "SRv6.";
      }
      enum "sd-wan" {
        value 5;
        description
          "SD-WAN.";
      }
    }
    description
      "Encapsulation type of packets.";
  }

  typedef srv6-mode {
    type enumeration {
      enum "be" {
        value 1;
        description
          "SRv6 iteration mode is BE.";
      }
      enum "te" {
        value 2;
        description
          "SRv6 iteration mode is TE.";
      }
    }
    description
      "SRv6 mode is BE or TE.";
  }

  typedef add-path-cap-type {
    type enumeration {
      enum "receive" {
        value 1;
        description
          "Support receiving add-path routes.";
      }
      enum "send" {
        value 2;
        description
          "Support sending add-path routes.";
      }
      enum "both" {
        value 3;
        description
          "Support receiving and sending add-path routes.";
      }
    }
    description
      "The type of add-path routes.";
  }

  typedef config-type {
    type enumeration {
      enum "default" {
        value 0;
        description
          "Disable or inheritance group.";
      }
      enum "enable" {
        value 1;
        description
          "Explicit config enable.";
      }
      enum "disable" {
        value 2;
        description
          "Explicit config disable.";
      }
    }
    description
      "Route server client.";
  }

  typedef route-limit-type {
    type enumeration {
      enum "noparameter" {
        value 0;
        description
          "Default value.";
      }
      enum "alert-only" {
        value 1;
        description
          "An alarm is generated and no additional routes will be accepted if the maximum number of routes allowed have been received.";
      }
      enum "idle-forever" {
        value 2;
        description
          "The connection that is interrupted is not automatically re-established if the maximum number of routes allowed have been received.";
      }
      enum "idle-timeout" {
        value 3;
        description
          "After the number of received routes exceeds the threshold and the timeout timer expires, the connection that is interrupted is automatically re-established.";
      }
    }
    description
      "The type of route limit.";
  }

  typedef es-ad-compatible-type {
    type enumeration {
      enum "default" {
        value 0;
        description
          "Default ES AD compatible.";
      }
      enum "enable" {
        value 1;
        description
          "Enable ES AD compatible.";
      }
      enum "disable" {
        value 2;
        description
          "Disable ES AD compatible.";
      }
    }
    description
      "Ethernet A-D per ES Route compatible type.";
  }

  typedef peer-comm-config-type {
    type enumeration {
      enum "default" {
        value 0;
        description
          "Configuration on peer was default.";
      }
      enum "enable" {
        value 1;
        description
          "Configuration on peer was enable.";
      }
      enum "disable" {
        value 2;
        description
          "Configuration on peer was disable.";
      }
    }
    description
      "State of the configuration on peer.";
  }

  typedef evpn-next-hop-mode {
    type enumeration {
      enum "null" {
        value 0;
        description
          "The next hop is not changed.";
      }
      enum "local" {
        value 1;
        description
          "The next hop is changed to the local IP address.";
      }
      enum "invariable" {
        value 2;
        description
          "Prevent the device from changing the next hop of each imported IGP route when advertising it to its EVPN peers.";
      }
    }
    description
      "BGP EVPN peer and peer group next hop mode.";
  }

  typedef apply-label-type {
    type enumeration {
      enum "per-route" {
        value 0;
        description
          "Per-route label allocation.";
      }
      enum "per-nexthop" {
        value 1;
        description
          "Per-next-hop label allocation.";
      }
    }
    description
      "BGP EVPN apply label type.";
  }

  typedef select-depend-type {
    type enumeration {
      enum "depend-tunnel" {
        value 1;
        description
          "Routing-dependent tunnel iteration.";
      }
      enum "depend-ip" {
        value 2;
        description
          "Routing-dependent IP iteration.";
      }
    }
    description
      "The type of nexthop select depend.";
  }

  typedef select-depend-type-ext {
    type enumeration {
      enum "depend-tunnel" {
        value 1;
        description
          "Routing-dependent tunnel iteration.";
      }
      enum "depend-ip" {
        value 2;
        description
          "Routing-dependent IP iteration.";
      }
      enum "depend-none" {
        value 3;
        description
          "Routing-dependent ignore.";
      }
    }
    description
      "The type of nexthop select depend.";
  }

  typedef import-vpn-rib-afi-type {
    type enumeration {
      enum "ipv4vpn" {
        value 3;
        description
          "IPv4 vpn address family.";
      }
      enum "ipv6vpn" {
        value 6;
        description
          "IPv6 vpn address Family.";
      }
    }
    description
      "The address family type of import rib.";
  }

  typedef import-rib-nhp-type {
    type enumeration {
      enum "mpls" {
        value 1;
        description
          "MPLS tunnels, include LDP, TE, SR-TE, SR-MPLS BE.";
      }
      enum "srv6" {
        value 2;
        description
          "Segment routing IPv6 tunnel.";
      }
    }
    description
      "The nexthop type of import rib.";
  }

  typedef evpn-route-type {
    type enumeration {
      enum "ip-prefix" {
        value 1;
        description
          "Ip prefix route.";
      }
    }
    description
      "The route type of evpn rib.";
  }

  typedef ad-prefix {
    type string {
      length "1..60";
    }
    description
      "An EVPN auto-discovery route prefix has the following formats:
       Ethernet auto-discovery route. The value is in the format of xxxx.xxxx.xxxx.xxxx.xxxx:M, where:
       - xxxx.xxxx.xxxx.xxxx.xxxx indicates the ESI configured for the device originating this route.
       - M is form 0 to 4294967295.";
  }

  typedef mac-prefix {
    type string {
      length "1..60";
    }
    description
      "An EVPN mac route prefix has the following formats:
       MAC advertisement route. The value is in the format of E:M:H-H-H:L:X.X.X.X or E:M:H-H-H:L: [X:X::X:X], where:
       - E indicates the ID of the VLAN to which the MAC address belongs.
       - M is fixed at 48, indicating the length of the MAC address.
       - H-H-H indicates the MAC address. The value is a 12-digit hexadecimal number, in the format of H-H-H. Each H is 4 digits. If an H contains fewer than 4 digits, the left-most digits are padded with zeros.
       - L indicating the mask length of the IP address corresponding to the MAC address.
       - X.X.X.X indicates the IP address corresponding to the MAC address.
       - X:X::X:X indicates the IPv6 address corresponding to the MAC address.";
  }

  typedef inclusive-prefix {
    type string {
      length "1..60";
    }
    description
      "An EVPN ethernet segment route prefix has the following formats:
       Inclusive multicast route. The value is in the format of M:L:X.X.X.X, where:
       - M indicates the EthTagId configured for the device originating the route.
       - X.X.X.X indicates the source address configured for the device originating the route.
       - L indicates the mask length of the source address configured for the device originating the route.";
  }

  typedef es-prefix {
    type string {
      length "1..80";
    }
    description
      "An EVPN ethernet segment route prefix has the following formats:
       Ethernet segment route. The value is in the format of xxxx.xxxx.xxxx.xxxx.xxxx or xxxx.xxxx.xxxx.xxxx.xxxx:L:X.X.X.X or xxxx.xxxx.xxxx.xxxx.xxxx:L:[X:X::X:X], where:
       - xxxx.xxxx.xxxx.xxxx.xxxx indicates the ESI configured for the device originating this route. x is a hexadecimal integer ranging from 0 to F.
       - L indicates the mask length of the source address configured for the device originating the route.
       - X.X.X.X indicates the IP address corresponding to the device originating the route.
       - X:X::X:X indicates the IPv6 address corresponding to the device originating the route.";
  }

  typedef evpn-ip-prefix {
    type string {
      length "1..60";
    }
    description
      "An EVPN ip prefix route prefix has the following formats:
       IP Prefix route. The value is in the format of L:X.X.X.X:M or L:[X:X::X:X]:M, where:
       - L is fixed at 0.
       - X.X.X.X indicates the ip address of host routes.
       - M indicates the mask length of host routes.
       - X:X::X:X indicates the IPv6 address of host routes.";
  }

  typedef tunnel-combination-type {
    type enumeration {
      enum "srv6-mpls" {
        value 1;
        description
          "SRv6 and MPLS combination.";
      }
    }
    description
      "The type of tunnel combination.";
  }

  typedef evpn-rib-encap-type {
    type enumeration {
      enum "mpls" {
        value 1;
        description
          "MPLS.";
      }
    }
    description
      "Encapsulation type of packets.";
  }

  typedef apply-sid-mode-evpn-rib {
    type enumeration {
      enum "per-route" {
        value 1;
        description
          "Set apply sid per route mode.";
      }
      enum "per-nexthop" {
        value 2;
        description
          "Set apply sid per nexthop mode.";
      }
    }
    description
      "Apply SID for evpn RIB.";
  }

  typedef esi {
    type string {
      length "1..24";
      pattern "( *(0[0-1]([0-9a-fA-F]){2}\\.(([0-9a-fA-F]){4}\\.){3}(([0-9a-fA-F]){4}))? *)";
    }
    description
      "ESI is begin with a-f or A-f or 0-9.";
  }

  typedef slow-delete-sid-af-type {
    type enumeration {
      enum "ipv4uni" {
        value 1;
        description
          "IPv4 unicast address family.";
      }
      enum "ipv6uni" {
        value 5;
        description
          "IPv6 unicast address family.";
      }
    }
    description
      "The address family type of slow-delete-sid.";
  }

  typedef vpn-type {
    type enumeration {
      enum "l3-vpn" {
        value 1;
        description
          "L3 vpn.";
      }
    }
    description
      "Vpn type.";
  }

  typedef cross-route-type {
    type enumeration {
      enum "esad" {
        value 1;
        description
          "Esad route.";
      }
    }
    description
      "Cross route type.";
  }

  typedef include-esi-type {
    type enumeration {
      enum "type4-esi" {
        value 1;
        description
          "Include type4 esi.";
      }
    }
    description
      "Include esi type.";
  }

  typedef evpn-route-type-flag {
    type bits {
      bit ibgp {
        description
          "IBGP route.";
      }
      bit ebgp {
        description
          "EBGP route.";
      }
      bit network {
        description
          "Network route.";
      }
      bit import {
        description
          "Imported route.";
      }
      bit auto-summary {
        description
          "Automatically summarized route.";
      }
      bit local-generate {
        description
          "Locally generated route.";
      }
      bit cpri {
        description
          "Route received by CBGP from PD-BGP.";
      }
      bit pcri {
        description
          "Route received by PD-BGP from CBGP.";
      }
      bit suppressed {
        description
          "Suppressed.";
      }
      bit nhp-empty {
        description
          "NHP-empty.";
      }
      bit no-adv {
        description
          "Routes that are not advertised to other routers.";
      }
      bit local-cross {
        description
          "Locally crossed routes.";
      }
      bit remote-cross {
        description
          "Remotely crossed routes.";
      }
      bit vd-bgp {
        description
          "VD-BGP route.";
      }
      bit path-local {
        description
          "Path_Local route.";
      }
      bit path-gateway {
        description
          "Path_Gateway route.";
      }
      bit policy-nopass {
        description
          "Policy_NoPass route.";
      }
      bit supprenet {
        description
          "Supernet route.";
      }
      bit dampened {
        description
          "Dampened route.";
      }
      bit history {
        description
          "History route.";
      }
      bit select {
        description
          "Selected route.";
      }
      bit best {
        description
          "Best route.";
      }
      bit backup {
        description
          "Backup route.";
      }
      bit attr-change {
        description
          "ATTR_Change route.";
      }
      bit nhlfe-created {
        description
          "NHLFE_Created route.";
      }
      bit ilm-created {
        description
          "ILM_Created route.";
      }
      bit nexthop-change {
        description
          "Route whose next hop changed.";
      }
      bit invalid {
        description
          "Invalid route.";
      }
      bit source-change {
        description
          "Route whose source address changed.";
      }
      bit in-selectedq {
        description
          "Route in a selected queue.";
      }
      bit exitif-error {
        description
          "EXITIF_ERROR route.";
      }
      bit group-head {
        description
          "GROUP_HEAD route.";
      }
    }
    description
      "EVPN-route-type-flag.";
  }

  grouping routing-table-type {
    description
      "Routing table information.";
    leaf nexthop {
      type inet:ip-address-no-zone;
      description
        "Next-hop address to which packets are sent.";
    }
    leaf local-preference {
      type uint32;
      description
        "Local priority. The attribute is only fit for the routes from IBGP peer, not suit for which of EBGP peer.";
    }
    leaf preferred-value {
      type uint32 {
        range "0..4294967295";
      }
      description
        "Preferred value of a protocol.";
    }
    leaf preference {
      type uint8 {
        range "0..255";
      }
      description
        "Preference of a route.";
    }
    leaf worse-reason {
      type string {
        length "1..50";
      }
      description
        "Reason why a route is not selected.";
    }
    leaf origin {
      type bgp-rt:bgp-origin-type;
      description
        "Origin of a route.";
    }
    leaf med {
      type uint32 {
        range "0..4294967295";
      }
      description
        "Route MED in the attribute node. The attribute is only fit for the routes from EBGP peer, not suit for which of IBGP peer.";
    }
    leaf flag-string {
      type string {
        length "1..100";
      }
      description
        "Route flag that contains a string of characters.";
    }
    leaf time {
      type uint32;
      units "s";
      description
        "Route duration time.";
    }
    leaf interface-name {
      type string {
        length "1..63";
      }
      description
        "Name of the outbound interface of a route.";
    }
    leaf remote-route-id {
      type inet:ipv4-address-no-zone;
      description
        "Router ID of a peer.";
    }
    leaf relay-nexthop {
      type inet:ip-address-no-zone;
      description
        "Iterated next hop.";
    }
    leaf relay-tunnel-name {
      type string {
        length "1..44";
      }
      description
        "Name of an iteration tunnel.";
    }
    leaf originator {
      type inet:ipv4-address-no-zone;
      description
        "Router ID of the route initiator.";
    }
  }

  grouping routing-table-type-attrid {
    description
      "Routing table information without attribute info.";
    leaf nexthop {
      type inet:ip-address-no-zone;
      description
        "Next-hop address to which packets are sent.";
    }
    leaf worse-reason {
      type string {
        length "1..50";
      }
      description
        "Reason why a route is not selected.";
    }
    leaf flag-string {
      type string {
        length "1..100";
      }
      description
        "Route flag that contains a string of characters.";
    }
    leaf time {
      type uint32;
      units "s";
      description
        "Route duration time.";
    }
    leaf interface-name {
      type string {
        length "1..63";
      }
      description
        "Name of the outbound interface of a route.";
    }
    leaf remote-route-id {
      type inet:ipv4-address-no-zone;
      description
        "Router ID of a peer.";
    }
    leaf relay-nexthop {
      type inet:ip-address-no-zone;
      description
        "Iterated next hop.";
    }
    leaf relay-tunnel-name {
      type string {
        length "1..44";
      }
      description
        "Name of an iteration tunnel.";
    }
  }

  grouping relay-aigp-type {
    description
      "Relay aigp information.";
    leaf relay-aigp {
      type uint32;
      description
        "Aigp attribute carried in a BGP LSP tunnel.";
    }
  }

  grouping irb-asymmetric-grp {
    description
      "Configure IRB asymmetric mode.";
    leaf irb-asymmetric {
      type empty;
      description
        "Enable IRB asymmetric.";
    }
    leaf policy-name {
      when "../irb-asymmetric";
      type leafref {
        path "/rtp:routing-policy/rtp:policy-definitions/rtp:policy-definition/rtp:name";
      }
      description
        "The name of IRB asymmetric route policy.";
    }
  }

  grouping policy-type-grp {
    description
      "Set route policy or filter.";
    choice import-policy-type {
      description
        "Set route policy or filter.";
      case rtp-ref {
        description
          "Route policy.";
        leaf import-policy {
          type leafref {
            path "/rtp:routing-policy/rtp:policy-definitions/rtp:policy-definition/rtp:name";
          }
          description
            "Specify the filtering policy applied to the routes learned from a peer. By default, no such policy is specified.";
        }
      }
    }
    choice export-policy-type {
      description
        "Set route policy or filter.";
      case rtp-ref {
        description
          "Route policy.";
        leaf export-policy {
          type leafref {
            path "/rtp:routing-policy/rtp:policy-definitions/rtp:policy-definition/rtp:name";
          }
          description
            "Specify the filtering policy applied to the routes to be advertised to a peer. By default, no such policy is specified.";
        }
      }
    }
  }

  grouping policy-type-grp-base {
    description
      "Set route policy or filter.";
    choice import-policy-type {
      description
        "Set route policy or filter.";
      case rtp-ref {
        description
          "Route policy.";
        leaf import-policy {
          type leafref {
            path "/rtp:routing-policy/rtp:policy-definitions/rtp:policy-definition/rtp:name";
          }
          description
            "Specify the filtering policy applied to the routes learned from a peer. By default, no such policy is specified.";
        }
      }
      case xpl-ref {
        description
          "Route filter.";
        container import-filter {
          description
            "Configure an import route-filter to filter the routes received from a peer group. By default, no route-filter is specified to filter the routes imported from a peer group.";
          leaf name {
            type leafref {
              path "/xpl:xpl/xpl:route-filters/xpl:route-filter/xpl:name";
            }
            description
              "Specify an import route-filter name.";
          }
          leaf parameter {
            when "../name";
            type xpl:filter-parameter-type;
            description
              "Specify an import route-filter parameter.";
          }
        }
      }
    }
    choice export-policy-type {
      description
        "Set route policy or filter.";
      case rtp-ref {
        description
          "Route policy.";
        leaf export-policy {
          type leafref {
            path "/rtp:routing-policy/rtp:policy-definitions/rtp:policy-definition/rtp:name";
          }
          description
            "Specify the filtering policy applied to the routes to be advertised to a peer. By default, no such policy is specified.";
        }
      }
      case xpl-ref {
        description
          "Route filter.";
        container export-filter {
          description
            "Configure an export route-filter to filter the routes to be advertised to a peer group. By default, no route-filter is specified to filter the routes to be advertised to a peer group.";
          leaf name {
            type leafref {
              path "/xpl:xpl/xpl:route-filters/xpl:route-filter/xpl:name";
            }
            description
              "Specify an export route-filter name.";
          }
          leaf parameter {
            when "../name";
            type xpl:filter-parameter-type;
            description
              "Specify an export route-filter parameter.";
          }
        }
      }
    }
  }

  grouping advertise-grp {
    description
      "Advertise common nodes.";
    leaf advertise-arp {
      type boolean;
      default "false";
      description
        "Enable/disable the advertise ARP route when its value is true.";
    }
    leaf advertise-irb {
      type boolean;
      default "false";
      description
        "Enable/disable the advertise IRB route when its value is true.";
    }
    leaf advertise-irbv6 {
      type boolean;
      default "false";
      description
        "Enable/disable the advertise IRBv6 route when its value is true.";
    }
    leaf advertise-nd {
      type boolean;
      default "false";
      description
        "Enable/disable the advertise ND route when its value is true.";
    }
  }

  grouping reoriginated-route-grp {
    description
      "Reoriginated route common nodes.";
    leaf reoriginated-mac-route {
      type boolean;
      default "false";
      description
        "Enable/disable MAC route regeneration and advertisement.";
    }
    leaf reoriginated-mac-ip-route {
      type boolean;
      default "false";
      description
        "Enable/disable MAC-IP route regeneration and advertisement.";
    }
    leaf reoriginated-mac-ipv6-route {
      type boolean;
      default "false";
      description
        "Enable/disable reoriginating IRBv6 route of EVPN.";
    }
    leaf reoriginated-ip-route {
      type boolean;
      default "false";
      description
        "Enable/disable IP route regeneration and advertisement.";
    }
    leaf reoriginated-ipv6-route {
      type boolean;
      default "false";
      description
        "Enable/disable reoriginating IPv6 prefix route of EVPN.";
    }
  }

  grouping routing-table-advertise-nexthop {
    description
      "BGP routing-table attributes.";
    leaf advertise-nexthop {
      type inet:ip-address-no-zone;
      description
        "Advertise next hop.";
    }
  }

  grouping evpn-prefix-sid-type {
    description
      "Information about prefix SID.";
    leaf prefix-sid {
      type inet:ipv6-address-no-zone;
      description
        "Prefix-SID attribute.";
    }
    leaf prefix-sid-structure {
      type string {
        length "1..36";
      }
      description
        "Prefix-SID structure attribute.";
    }
    leaf prefix-sid-behavior {
      type string {
        length "1..32";
      }
      description
        "Endpoint behavior of Prefix-SID.";
    }
  }

  grouping evpn-bypass-prefix-sid-type {
    description
      "Information about bypass prefix SID.";
    leaf bypass-prefix-sid {
      type inet:ipv6-address-no-zone;
      description
        "Bypass Prefix-SID attribute.";
    }
    leaf bypass-prefix-sid-structure {
      type string {
        length "1..36";
      }
      description
        "Bypass Prefix-SID structure attribute.";
    }
    leaf bypass-prefix-sid-behavior {
      type string {
        length "1..32";
      }
      description
        "Endpoint behavior of bypass Prefix-SID.";
    }
  }

  grouping evpn-l3-prefix-sid-type {
    description
      "Information about l3 prefix SID.";
    leaf l3-prefix-sid {
      type inet:ipv6-address-no-zone;
      description
        "L3 Prefix-SID attribute.";
    }
    leaf l3-prefix-sid-structure {
      type string {
        length "1..36";
      }
      description
        "L3 Prefix-SID structure attribute.";
    }
    leaf l3-prefix-sid-behavior {
      type string {
        length "1..32";
      }
      description
        "Endpoint behavior of L3 Prefix-SID.";
    }
  }

  grouping bestroute-nh-relay-pri-grp {
    description
      "Nexthop relay during the best route selection.";
    container bestroute-nexthop-recursive-priority {
      description
        "Configure BGP nexthop iteration priority in route selection.";
      leaf nexthop-recursive-srv6-te-policy {
        type empty;
        description
          "Enable/disable BGP to compare nexthop iteration SRv6-TE Policy before iteration SRv6 BE and IPv6 in route selection.";
      }
    }
  }

  augment "/ni:network-instance/ni:instances/ni:instance/bgp:bgp/bgp:base-process/bgp:peers/bgp:peer/bgp:afs/bgp:af" {
    description
      "Augment for an L2VPN instance and EVPN association.";
    container l2vpn-evpn {
      when "../bgp:type = 'evpn' and ../../../../../../../ni:name='_public_'";
      must "(all-route-limit='true' and mac-route-limit='false' and route-limit) or (all-route-limit='false' and mac-route-limit='true' and route-limit) or (all-route-limit='false' and mac-route-limit='false')";
      must "not(advertise-arp = 'true' and advertise-irb = 'true')";
      must "not(advertise-nd = 'true' and advertise-irbv6 = 'true')";
      description
        "Configure peer EVPN.";
      leaf group-name {
       
        type leafref {
          path "../../../../../../bgp:peer-groups/bgp:peer-group/bgp:name";
        }
        must "(../../../../../../bgp:peer-groups/bgp:peer-group[bgp:name=current()]/bgp:type = 'ibgp' and ../../../../bgp:remote-as = /bgp:bgp/bgp:base-process/bgp:as) or (../../../../../../bgp:peer-groups/bgp:peer-group[bgp:name=current()]/bgp:type = 'ebgp' and ../../../../bgp:remote-as != /bgp:bgp/bgp:base-process/bgp:as)";
        must "../../../../../../bgp:peer-groups/bgp:peer-group[bgp:name=current()]/bgp:afs/bgp:af[bgp:type='evpn']";
        must "../../../../../../bgp:peer-groups/bgp:peer-group[bgp:name=current()]/bgp:peer-establish-mode = 'static'";
        description
          "Configure a name for a peer group. By default, BGP peers join no peer group. BGP peers distinguish the peer group type when joining a peer group. IBGP peers cannot join an EBGP peer group. After a peer is deleted from the peer group, the peer is disabled from the address family. The object cannot be modified.";
      }
      leaf allow-as-loop {
        type uint8 {
          range "1..10";
        }
        description
          "Allow repetitive local AS numbers. By default, repetitive local AS numbers are not allowed.";
      }
      leaf reflect-client {
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      uses policy-type-grp-base;
      leaf advertise-community {
        type boolean;
        default "false";
        description
          "Enable/disable advertise community attribute to a peer or peer group.";
      }
      leaf advertise-large-community {
        type config-type;
        default "default";
        description
          "Enable large-community attribute advertisement. By default, the function is not configured on any peer. The Link-state address family and the RPD address family do not support this element.";
      }
      uses advertise-grp;
      leaf advertise-encap-type {
        type advertise-encap-type;
        must "(not(contains(../../../../bgp:address,':')) and (../advertise-encap-type != 'srv6')) or (contains(../../../../bgp:address,':') and (../advertise-encap-type != 'sd-wan'))";
        default "mpls";
        description
          "Encapsulation type of packets.";
      }
      leaf advertise-add-path-mode {
        type add-path-cap-type;
        description
          "Enable add-path route advertisement to a peer.";
      }
      leaf advertise-add-path-num {
        type uint8 {
          range "2..128";
        }
        description
          "Number of add-path routes that can be advertised to a peer.";
      }
      leaf advertise-suppressed-route {
        type boolean;
        default "false";
        description
          "Enable/disable advertising suppressed-detail-route.";
      }
      leaf advertise-suppressed-route-status {
        type boolean;
        default "false";
        config false;
        description
          "The effective status of advertising suppressed-detail-route.";
      }
      leaf all-route-limit {
        type boolean;
        default "false";
        description
          "Enable/disable all routing overflow alarm received from the specified peer.";
      }
      leaf mac-route-limit {
        type boolean;
        default "false";
        description
          "Enable/disable MAC routing overflow alarm received from the specified peer.";
      }
      leaf route-limit {
        when "(../all-route-limit='true' or ../mac-route-limit='true')";
        type uint32 {
          range "1..4294967295";
        }
        description
          "Configure the maximum number of routes that can be accepted from a peer.";
      }
      leaf route-limit-percent {
        when "../route-limit";
        type uint8 {
          range "1..100";
        }
        default "75";
        description
          "Specify the percentage of routes when a router starts to generate an alarm.";
      }
      leaf route-limit-type {
        when "../route-limit";
        type route-limit-type;
        must "(../route-limit-type = 'idle-timeout' and ../route-limit-idle-timeout) or (../route-limit-type = 'alert-only') or (../route-limit-type = 'idle-forever') or (../route-limit-type = 'noparameter')";
        default "noparameter";
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        when "../route-limit-type = 'idle-timeout'";
        type uint16 {
          range "1..1200";
        }
        units "min";
        description
          "Enable/disable specify the value of the idle-timeout timer to automatically reestablish the connections after they are cut off when the number of routes exceeds the set threshold.";
      }
      leaf route-update-interval {
       
        type uint16 {
          range "0..600";
        }
        units "s";
        description
          "Specify the minimum interval at which Update packets are sent. By default, the interval at which Update packets are sent to IBGP peers is 15s, and the interval at which Update packets are sent to EBGP peers is 30s.";
      }
      leaf reoriginate-route-enable {
        type boolean;
        default "false";
        description
          "Enable/disable route regeneration.";
      }
      leaf reoriginate-vpnv4-route {
        type boolean;
        default "false";
        description
          "Enable/disable VPNv4 route regeneration and advertisement.";
      }
      leaf reoriginate-mac-route {
        type boolean;
        default "false";
        description
          "Enable/disable MAC route regeneration and advertisement.";
      }
      leaf reoriginate-mac-ip-route {
        type boolean;
        default "false";
        description
          "Enable/disable MAC-IP route regeneration and advertisement.";
      }
      leaf reoriginate-mac-ipv6-route {
        type boolean;
        default "false";
        description
          "Enable/disable reoriginating IRBv6 route of EVPN.";
      }
      leaf reoriginate-ip-route {
        type boolean;
        default "false";
        description
          "Enable/disable IP route regeneration and advertisement.";
      }
      leaf reoriginate-ipv6-route {
        type boolean;
        default "false";
        description
          "Enable/disable reoriginating IPv6 prefix route of EVPN.";
      }
      leaf reoriginate-vpnv6-route {
        type boolean;
        default "false";
        description
          "Enable/disable reoriginating the route of VPNv6.";
      }
      leaf graceful-restart-static-timer {
        type uint32 {
          range "3600..2147483647";
        }
        units "s";
        description
          "Specifies the maximum time during which a peer waits for a BGP session reestablishment.";
      }
      leaf es-ad-compatible {
        type es-ad-compatible-type;
        default "default";
        description
          "Ethernet A-D per ES Route Compatible.";
      }
      leaf split-group-name {
        type string {
          length "1..31";
        }
        description
          "Split group name.";
      }
      leaf vpn-orf-disable {
        type boolean;
        default "false";
        description
          "Enable/disable VPN ORF.";
      }
      leaf upe-enable {
        type boolean;
        default "false";
        description
          "Enable/disable the peer as an underlayer PE (UPE).";
      }
      leaf next-hop-mode {
        type evpn-next-hop-mode;
        default "null";
        description
          "Enable next hop mode.";
      }
      leaf high-priority {
        type peer-comm-config-type;
        default "default";
        description
          "Enable a higher priority to a specified peer.";
      }
      leaf high-priority-status {
        type boolean;
        default "false";
        config false;
        description
          "The effective status of higher priority to a specified peer.";
      }
      leaf preferred-value {
        type uint32 {
          range "0..65535";
        }
        default "0";
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type bgp:peer-attr-enable-type;
        description
          "Enable/disable only advertising evpn detailed mac-route.";
      }
      leaf mac-detail-route-only-status {
        type boolean;
        config false;
        description
          "The effective status of advertising evpn detailed mac-route.";
      }
      leaf peer-as-check {
        type bgp:peer-attr-enable-type;
        description
          "Enable/disable BGP to prevents the routes received from an EBGP peer from being broadcast to other peers with the same AS number.";
      }
      leaf advertise-srv6-locator {
        when "../advertise-encap-type='srv6'";
        type empty;
        description
          "Advertise SRv6 locator.";
      }
      leaf transposition-mode {
        when "../advertise-srv6-locator";
        type empty;
        description
          "Enable/disable advertising prefix SIDs with transposition offset and length.";
      }
      leaf transit-med-to-ebgp {
        type bgp:peer-attr-enable-type;
        description
          "Transmits the MED attribute to EBGP peers.";
      }
      uses bgp:peer-independent-peer-group-type;
      leaf keep-all-routes {
        type boolean;
        default "false";
        description
          "Enable/disable saving all the updated information about BGP routes from a specified peer or peer group after a BGP connection is established, even though these BGP routes fail to match the routing policy on the ingress. By default, the updated information about BGP routes from a specified peer is saved only when the routes match the routing policy on the ingress. If a router supports route refreshing, this option is not required.";
      }
      container option {
        description
          "Configure bgp evpn peer extended options.";
        leaf srv6-label-compatible {
          type bgp:peer-attr-enable-type;
          must "contains(../../../../../bgp:address,':')";
          description
            "Enable SRv6 label compatible.";
        }
        leaf srv6-inclusive-label-compatible {
          type bgp:peer-attr-enable-type;
          must "contains(../../../../../bgp:address,':')";
          description
            "Enable SRv6 inclusive routes label compatible.";
        }
        leaf unique-source-ip-prefix {
          type bgp:peer-attr-enable-type;
          description
            "Enable the unique source function.";
        }
        leaf advertise-ip-esad {
          type bgp:peer-attr-enable-type;
          must "../xsec and contains(../../../../../bgp:address,':') and ../../advertise-encap-type = 'srv6' and ../../../../../bgp:ssl-policy/bgp:name and ((../../../../../bgp:ssl-policy/bgp:role = 'server' and ../../../../../bgp:ssl-policy/bgp:server-certificate = 'enable') or (../../../../../bgp:ssl-policy/bgp:role = 'client'))";
          description
            "Enable EVPN advertise ESAD route.";
        }
        leaf xsec {
          when "../advertise-ip-esad = 'enable'";
          type empty;
          description
            "Enable EVPN advertise route with Xsec attribute.";
        }
      }
      container effect-state {
        config false;
        description
          "Operational state of peer.";
        leaf advertise-srv6-locator {
          type boolean;
          description
            "Whether to advertise SRv6 locators on the EVPN peer.";
        }
        leaf transit-med-to-ebgp {
          type boolean;
          description
            "Transmits the MED attribute to EBGP peers.";
        }
      }
      uses bgp:path-attr-map-type;
      container default-route-originates {
        description
          "List of default EVPN routes.";
        list default-route-originate {
          key "vpn-name type";
          description
            "Configure the advertisement of default EVPN routes.";
          leaf vpn-name {
            type leafref {
              path "/ni:network-instance/ni:instances/ni:instance/ni:name";
            }
            must "../vpn-name!='_public_'";
            description
              "VPN instance name. It uniquely identifies a VPN instance. The name is a string of case-sensitive characters.";
          }
          leaf type {
            type l3vpn:af-type;
            must "../type!='ipv4-unicast' or (/ni:network-instance/ni:instances/ni:instance[ni:name=current()/../vpn-name]/l3vpn:afs/l3vpn:af[l3vpn:type='ipv4-unicast']/l3vpn:route-distinguisher or (/ni:network-instance/ni:instances/ni:instance[ni:name=current()/../vpn-name]/l3vpn:afs/l3vpn:af[l3vpn:type='ipv4-unicast'] and /ni:network-instance/ni:global/ni:route-distinguisher-auto-ip))";
            must "../type!='ipv6-unicast' or (/ni:network-instance/ni:instances/ni:instance[ni:name=current()/../vpn-name]/l3vpn:afs/l3vpn:af[l3vpn:type='ipv6-unicast']/l3vpn:route-distinguisher or (/ni:network-instance/ni:instances/ni:instance[ni:name=current()/../vpn-name]/l3vpn:afs/l3vpn:af[l3vpn:type='ipv6-unicast'] and /ni:network-instance/ni:global/ni:route-distinguisher-auto-ip))";
            description
              "Default EVPN route type.";
          }
          leaf enable {
            type boolean;
            default "false";
            description
              "Enable/disable the advertisement of default EVPN routes.";
          }
        }
      }
    }
  }
  augment "/ni:network-instance/ni:instances/ni:instance/bgp:bgp/bgp:base-process/bgp:peer-groups/bgp:peer-group/bgp:afs/bgp:af" {
    description
      "Augment for an L2VPN instance and EVPN association.";
    container l2vpn-evpn {
      when "(../bgp:type = 'evpn' and ../../../../../../../ni:name='_public_')";
      must "(all-route-limit='true' and mac-route-limit='false' and route-limit) or (all-route-limit='false' and mac-route-limit='true' and route-limit) or (all-route-limit='false' and mac-route-limit='false')";
      must "not(advertise-arp = 'true' and advertise-irb = 'true')";
      must "not(advertise-nd = 'true' and advertise-irbv6 = 'true')";
      description
        "Configure EVPN peer group.";
      leaf allow-as-loop {
        type uint8 {
          range "1..10";
        }
        description
          "Allow repetitive local AS numbers. By default, repetitive local AS numbers are not allowed.";
      }
      leaf reflect-client {
        when "../../../../bgp:type = 'ibgp'";
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      uses policy-type-grp-base;
      leaf es-ad-compatible {
        type boolean;
        default "false";
        description
          "Enable/disable ethernet A-D per ES route compatible.";
      }
      leaf split-group-name {
        type string {
          length "1..31";
        }
        description
          "Split group name.";
      }
      leaf vpn-orf-disable {
        type boolean;
        default "false";
        description
          "Enable/disable VPN ORF.";
      }
      leaf upe-enable {
        type boolean;
        default "false";
        description
          "Enable/disable the peer as an underlayer PE (UPE).";
      }
      leaf next-hop-mode {
        type evpn-next-hop-mode;
        default "null";
        description
          "Enable next hop mode.";
      }
      leaf advertise-community {
        type boolean;
        default "false";
        description
          "Enable/disable an advertise the community attribute to a peer or peer group.";
      }
      leaf advertise-large-community {
        type boolean;
        default "false";
        description
          "Enable/disable large-community attribute advertisement. The Link-state address family and the RPD address family do not support this element.";
      }
      uses advertise-grp;
      leaf advertise-encap-type {
        type advertise-encap-type;
        default "mpls";
        description
          "Encapsulation type of packets.";
      }
      leaf advertise-suppressed-route {
        type boolean;
        default "false";
        description
          "Enable/disable advertising suppressed detail route.";
      }
      leaf advertise-add-path-mode {
        type add-path-cap-type;
        description
          "Enable add-path route advertisement to a peer.";
      }
      leaf advertise-add-path-num {
        type uint8 {
          range "2..128";
        }
        description
          "Number of add-path routes that can be advertised to a peer group.";
      }
      leaf all-route-limit {
        type boolean;
        default "false";
        description
          "Enable/disable all routing overflow alarm received from the specified peer.";
      }
      leaf mac-route-limit {
        type boolean;
        default "false";
        description
          "Enable/disable MAC routing overflow alarm received from the specified peer.";
      }
      leaf route-limit {
        when "(../all-route-limit='true' or ../mac-route-limit='true')";
        type uint32 {
          range "1..4294967295";
        }
        description
          "Configure the maximum number of routes that can be accepted from a peer.";
      }
      leaf route-limit-percent {
        when "../route-limit";
        type uint8 {
          range "1..100";
        }
        default "75";
        description
          "Specify the percentage of routes when a router starts to generate an alarm.";
      }
      leaf route-limit-type {
        when "../route-limit";
        type route-limit-type;
        must "(../route-limit-type = 'idle-timeout' and ../route-limit-idle-timeout) or (../route-limit-type = 'alert-only') or (../route-limit-type = 'idle-forever') or (../route-limit-type = 'noparameter')";
        default "noparameter";
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        when "../route-limit-type = 'idle-timeout'";
        type uint16 {
          range "1..1200";
        }
        units "min";
        description
          "Specify the value of the idle-timeout timer to automatically reestablish the connections after they are cut off when the number of routes exceeds the set threshold.";
      }
      leaf route-update-interval {
       
        type uint16 {
          range "0..600";
        }
        units "s";
        description
          "Specify the minimum interval at which Update packets are sent. By default, the interval at which Update packets are sent to IBGP peers is 15s, and the interval at which Update packets are sent to EBGP peers is 30s.";
      }
      leaf reoriginated-route-enable {
        type boolean;
        default "false";
        description
          "Enable/disable route regeneration.";
      }
      uses reoriginated-route-grp;
      leaf reoriginated-vpnv4-route {
        type boolean;
        default "false";
        description
          "Enable/disable VPNv4 route regeneration and advertisement.";
      }
      leaf reoriginated-vpnv6-route {
        type boolean;
        default "false";
        description
          "Enable/disable reoriginating the route of VPNv6.";
      }
      leaf high-priority {
        type boolean;
        default "false";
        description
          "Enable/disable routes received from a specified peer have a higher priority.";
      }
      leaf preferred-value {
        type uint32 {
          range "0..65535";
        }
        default "0";
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type boolean;
        default "false";
        description
          "Enable/disable only advertising evpn detailed mac-route.";
      }
      leaf advertise-srv6-locator {
        when "../advertise-encap-type='srv6'";
        type empty;
        description
          "Advertise SRv6 locator.";
      }
      leaf transposition-mode {
        when "../advertise-srv6-locator";
        type empty;
        description
          "Enable/disable advertising prefix SIDs with transposition offset and length.";
      }
      leaf transit-med-to-ebgp {
        when "../../../../bgp:type = 'ebgp'";
        type boolean;
        default "false";
        description
          "Enable/disable transmits the MED attribute to EBGP peers.";
      }
      leaf peer-as-check {
        when "../../../../bgp:type='ebgp'";
        type bgp:peer-attr-enable-type;
        default "disable";
        description
          "Enable/disable BGP to prevents the routes received from an EBGP peer from being broadcast to other peers with the same AS number.";
      }
      uses bgp:group-independent-peer-group-type;
      leaf keep-all-routes {
        type boolean;
        default "false";
        description
          "Enable/disable saving all the updated information about BGP routes from a specified peer or peer group after a BGP connection is established, even though these BGP routes fail to match the routing policy on the ingress. By default, the updated information about BGP routes from a specified peer is saved only when the routes match the routing policy on the ingress. If a router supports route refreshing, this option is not required.";
      }
      container option {
        description
          "Configure bgp evpn peer group extended options.";
        leaf srv6-label-compatible {
         
          type empty;
          status deprecated;
          description
            "Enable SRv6 label compatible. The leaf srv6-label-compatible is deprecated. You are advised to use the leaf srv6-label-compatible2.";
        }
        leaf srv6-inclusive-label-compatible {
         
          type empty;
          status deprecated;
          description
            "Enable SRv6 inclusive routes label compatible. The leaf srv6-inclusive-label-compatible is deprecated. You are advised to use the leaf srv6-inclusive-label-compatible2.";
        }
        leaf unique-source-ip-prefix {
          type empty;
          description
            "Enable the unique source function.";
        }
        leaf srv6-label-compatible2 {
          type bgp:peer-attr-enable-type;
          default "enable";
          description
            "Enable SRv6 label compatible.";
        }
        leaf srv6-inclusive-label-compatible2 {
          type bgp:peer-attr-enable-type;
          default "enable";
          description
            "Enable SRv6 inclusive routes label compatible.";
        }
        leaf advertise-ip-esad {
          type empty;
          must "../xsec and ../../advertise-encap-type = 'srv6' and ../../../../../bgp:ssl-policy/bgp:name and ((../../../../../bgp:ssl-policy/bgp:role = 'server' and ../../../../../bgp:ssl-policy/bgp:server-certificate) or (../../../../../bgp:ssl-policy/bgp:role = 'client'))";
          description
            "Enable EVPN advertise ESAD route.";
        }
        leaf xsec {
          when "../advertise-ip-esad";
          type empty;
          description
            "Enable EVPN advertise route with Xsec attribute.";
        }
      }
      container default-route-originates {
        description
          "List of default EVPN routes.";
        list default-route-originate {
          key "vpn-name type";
          description
            "Configure the advertisement of default EVPN routes.";
          leaf vpn-name {
            type leafref {
              path "/ni:network-instance/ni:instances/ni:instance/ni:name";
            }
            must "../vpn-name!='_public_'";
            description
              "VPN instance name. It uniquely identifies a VPN instance. The name is a string of case-sensitive characters.";
          }
          leaf type {
            type l3vpn:af-type;
            must "../type!='ipv4-unicast' or (/ni:network-instance/ni:instances/ni:instance[ni:name=current()/../vpn-name]/l3vpn:afs/l3vpn:af[l3vpn:type='ipv4-unicast']/l3vpn:route-distinguisher or (/ni:network-instance/ni:instances/ni:instance[ni:name=current()/../vpn-name]/l3vpn:afs/l3vpn:af[l3vpn:type='ipv4-unicast'] and /ni:network-instance/ni:global/ni:route-distinguisher-auto-ip))";
            must "../type!='ipv6-unicast' or (/ni:network-instance/ni:instances/ni:instance[ni:name=current()/../vpn-name]/l3vpn:afs/l3vpn:af[l3vpn:type='ipv6-unicast']/l3vpn:route-distinguisher or (/ni:network-instance/ni:instances/ni:instance[ni:name=current()/../vpn-name]/l3vpn:afs/l3vpn:af[l3vpn:type='ipv6-unicast'] and /ni:network-instance/ni:global/ni:route-distinguisher-auto-ip))";
            description
              "Default EVPN route type.";
          }
        }
      }
    }
  }
  augment "/ni:network-instance/ni:instances/ni:instance/bgp:bgp/bgp:base-process/bgp:afs/bgp:af" {
    description
      "Augment for an L2VPN instance and EVPN association.";
    container l2vpn-evpn {
      when "(../bgp:type = 'evpn') and (../../../../../ni:name='_public_')";
      description
        "Configure L2VPN-EVPN.";
      leaf policy-vpntarget {
        type boolean;
        default "true";
        description
          "Enable/disable VPN target-based filtering for the received VPN routes. By default, VPN target-based filtering is enabled. Only the VPN route whose Export RT attribute matches the local Import RT attribute can be added to the routing table. This option can be used in the inter-AS VPN Option B solution and the ASBR MP-EBGP inter-AS L2VPN solution in Kompella mode.";
      }
      leaf add-path-select-num {
        type uint8 {
          range "2..128";
        }
        description
          "Number of add-path routes.";
      }
      leaf label-free-delay {
        type uint8 {
          range "0..180";
        }
        units "s";
        default "5";
        description
          "Label free delay.";
      }
      leaf route-select-delay {
        type uint16 {
          range "0..3600";
        }
        units "s";
        default "0";
        description
          "Route selection delay.";
      }
      leaf exclusive-eviad-enable {
        when "../route-select-delay!=0";
        type boolean;
        default "false";
        description
          "Enable/disable route selection delay for non-EVI-AD routes.";
      }
      leaf inclusive-mac-enable {
        when "../route-select-delay!=0";
        type boolean;
        default "false";
        description
          "Enable/disable route selection delay for MAC routes.";
      }
      leaf label-per-nexthop {
        type apply-label-type;
        default "per-route";
        description
          "Apply label per nexthop enable.";
      }
      leaf auto-frr {
        type boolean;
        default "false";
        description
          "Enable/disable Auto FRR.";
      }
      leaf detection-threshold {
       
        type uint16 {
          range "120..3600";
        }
        default "300";
        status deprecated;
        description
          "Specify the time in seconds lagging behind average when a peer is determined to be a slow peer. The leaf detection-threshold is deprecated. You are advised to use the leaf '/ni:network-instance/ni:instances/ni:instance/bgp:bgp/bgp:base-process/bgp:afs/bgp:af/bgp-evpn:l2vpn-evpn/bgp-evpn:slow-peer/bgp-evpn:detection-threshold'.";
      }
      leaf absolute-detection-threshold {
       
        type uint16 {
          range "3..3600";
        }
        default "9";
        status deprecated;
        description
          "Specify the packet send delay time in second when a peer is determined to be a slow peer. The leaf absolute-detection-threshold is deprecated. You are advised to use the leaf '/ni:network-instance/ni:instances/ni:instance/bgp:bgp/bgp:base-process/bgp:afs/bgp:af/bgp-evpn:l2vpn-evpn/bgp-evpn:slow-peer/bgp-evpn:absolute-detection-threshold'.";
      }
      leaf tunnel-selector {
        type leafref {
          path "/rtp:routing-policy/rtp:tunnel-selectors/rtp:tunnel-selector/rtp:name";
        }
        description
          "Configure a tunnel selector and apply it to the BGP IPv4 unicast, BGP VPNv4 address families and BGP VPNv6 address families so that IPv4, VPNv4 and VPNv6 labeled routes can be iterated to tunnels based on the tunnel selector.";
      }
      leaf vpn-orf-enable {
        type boolean;
        default "false";
        description
          "Enable/disable VPN-ORF capability.";
      }
      leaf nexthop-select-depend-type {
        type select-depend-type-ext;
        default "depend-ip";
        description
          "In none mode, route selection does not depend on whether the next hop is reachable. In tunnel mode, the labeled EVPN route can participate in route selection only after its next hop is iterated to an LSP. In IP
           mode, the labeled EVPN route can participate in route selection only after its next hop is iterated to an IP address. By default, the labeled EVPN route can participate in route selection
           if its next hop can be iterated to an IP address, regardless of whether the LSP of the next hop exists. This allows the RR that is not enabled with MPLS to forward labeled routes. In non-RR
           networking or RR networking where the BGP next hop is changed, BGP needs to check whether there is an LSP destined for the next hop. If such an LSP is not found, BGP needs to establish an LSP in
           advance. If the default setting is adopted, a labeled EVPN route may be selected prior to LSP establishment. As a result, services are incorrectly switched before LSP establishment and
           service stability is affected. Therefore, allow route selection only after the labeled EVPN route is iterated to an LSP.";
      }
      leaf nexthop-resolve-aigp {
        type boolean;
        default "false";
        description
          "Enable/disable route selection using the AIGP attribute of the BGP LSP through which they are transmitted.";
      }
      leaf reflect-change-path {
        type boolean;
        default "false";
        description
          "Enable/disable an RR to use an export policy to change route AS_Path.";
      }
      leaf rr-ext-community-filter {
        type leafref {
          path "/rtp:routing-policy/rtp:ext-community-filters/rtp:ext-community-filter/rtp:name";
        }
        description
          "Set the name of the extended community filter supported by an RR group. For the purpose of load balancing, only the IBGP route whose route-target extended community attribute meets the matching rules can be reflected.";
      }
      leaf time-df-delay {
        type uint16 {
          range "0..1200";
        }
        units "s";
        default "60";
        description
          "Specifies forwarder election delay-timer value. In seconds.";
      }
      leaf reflect-between-client {
        type boolean;
        default "true";
        description
          "Enable/disable route reflection between clients. If clients of a route reflector (RR) are fully meshed, you can disable route reflection among clients to reduce the cost.";
      }
      leaf bestroute-igp-metric-ignore {
        type boolean;
        default "false";
        description
          "Enable/disable EVPN to ignore the IGP cost of each EVPN route to the next hop in route selection. By default, an EVPN route with a smaller IGP cost to the next hop is preferred.";
      }
      leaf inclusive-route-pmsi-compatible {
        type boolean;
        default "false";
        description
          "Enable/disable PMSI attribute compatibility for inclusive routes.";
      }
      leaf reflect-df-election-extcommunity-compatible {
        type boolean;
        default "false";
        description
          "Enable/disable reflect only one df-election extcommunity to peer.";
      }
      choice reflector-type {
        description
          "Set IPv4 address or id.";
        case address {
          description
            "IPv4 address.";
          leaf reflector-cluster-ipv4 {
            type inet:ipv4-address-no-zone;
            description
              "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
        case id {
          description
            "Set value.";
          leaf reflector-cluster-id {
            type uint32 {
              range "1..4294967295";
            }
            description
              "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
      }
      uses bgp:load-balancing-configuration;
      leaf vpn-orf-enhance-advertise {
        type boolean;
        default "false";
        description
          "Enable/disable the enhanced capability of route advertisement for VPN-ORF.";
      }
      container option {
        description
          "Configure address family common options.";
        uses bgp:option-group;
        leaf xsec-failure-action-plaintext {
          type empty;
          description
            "Enable/disable the function what forward the packet in plaintext when the Xsec fails.";
        }
        leaf route-lowest-priority-graceful-restart {
          type empty;
          description
            "Enable/disable reducing the priority of routes received from graceful-restart neighbors.";
        }
      }
      container remote-crosss {
        description
          "List of remote cross.";
        list remote-cross {
          key "vpn-type route-type include-esi-type";
          description
            "Configure the remote cross.";
          leaf vpn-type {
            type vpn-type;
            description
              "Configure the vpn type.";
          }
          leaf route-type {
            type cross-route-type;
            must "../vpn-type='l3-vpn'";
            description
              "Configure the route type.";
          }
          leaf include-esi-type {
            type include-esi-type;
            must "../route-type='esad'";
            description
              "Configure Include esi type.";
          }
        }
      }
      container nexthop-recursive-lookup {
        description
          "Configure next hop iteration.";
        container common {
          description
            "Configure next hop iteration common options.";
          leaf restrain {
            type boolean;
            default "true";
            description
              "Enable/disable the function to restrain next hop iteration in case of next hop flapping.";
          }
          choice policy-type {
            description
              "Set route policy.";
            case rtp-ref {
              description
                "Route policy.";
              leaf policy-name {
                type leafref {
                  path "/rtp:routing-policy/rtp:policy-definitions/rtp:policy-definition/rtp:name";
                }
                description
                  "Specify the name of a routing policy.";
              }
            }
            case xpl-ref {
              description
                "Route filter.";
              leaf filter-name {
                type leafref {
                  path "/xpl:xpl/xpl:route-filters/xpl:route-filter/xpl:name";
                }
                description
                  "Specify a route-filter name.";
              }
              leaf filter-parameter {
                when "../filter-name";
                type xpl:filter-parameter-type;
                description
                  "Specify a route-filter parameter.";
              }
            }
          }
          leaf default-route {
            type boolean;
            default "false";
            description
              "Enable/disable default route.";
          }
          leaf include-srv6-best-effort {
            type empty;
            must "../policy-name or ../filter-name";
            description
              "Enable routing policy application when the iteration result of a route's next-hop's next hop points to SRv6 BE.";
          }
        }
        uses bgp:nexthop-recursive-lookup-delay;
        container bit-error-detection {
          description
            "Configure EVPN bit-error detection parameters.";
          leaf enable {
            type boolean;
            must "(../enable='false') or (../enable='true' and (../med or ../local-preference))";
            default "false";
            description
              "Enable/disable association between bit error events and the adjustment of route attributes.";
          }
          leaf med {
            when "../enable='true'";
            type uint32 {
              range "1..4294967295";
            }
            description
              "Specify the MED adjustment for EVPN routes used when a bit error event occurs.";
          }
          leaf local-preference {
            when "../enable='true'";
            type uint32 {
              range "1..4294967295";
            }
            description
              "Specify the local preference adjustment for routes used when a bit error event occurs.";
          }
          choice policy-type {
            description
              "Set route-policy or route-filter for bit-error-triggered protection switching.";
            case rtp-ref {
              description
                "Route policy.";
              leaf route-policy {
                when "../enable='true'";
                type leafref {
                  path "/rtp:routing-policy/rtp:policy-definitions/rtp:policy-definition/rtp:name";
                }
                description
                  "Specify the name of route-policy for bit-error-triggered protection switching. The MED or local preference of only the routes that match the route-policy is adjusted.";
              }
            }
            case xpl-ref {
              description
                "Route filter.";
              leaf filter-name {
                when "../enable='true'";
                type leafref {
                  path "/xpl:xpl/xpl:route-filters/xpl:route-filter/xpl:name";
                }
                description
                  "Specify a route-filter name.";
              }
              leaf filter-parameter {
                when "../filter-name";
                type xpl:filter-parameter-type;
                description
                  "Specify a route-filter parameter.";
              }
            }
          }
        }
      }
      uses bgp:vrf-af-dampening-routes;
      uses bgp:slow-peer-type;
      container load-balancing {
        description
          "Configure the number of imported rib routes.";
        leaf maximum-load-balancing-import-rib {
          when "../../import-vpn-ribs";
          type uint16 {
            range "1..2";
          }
          default "1";
          description
            "Specify the maximum number of imported rib routes.";
        }
        container interworking-ribs {
          description
            "List of maximum number of equal-cost interworking RIB routes.";
          list interworking-rib {
            key "route-type";
            description
              "Configure the maximum number of equal-cost interworking RIB routes.";
            leaf route-type {
              type evpn-route-type;
              description
                "EVPN route type.";
            }
            leaf maximum {
              type uint8 {
                range "2";
              }
              mandatory true;
              description
                "Specify the maximum number of equal-cost interworking RIB routes.";
            }
          }
        }
      }
      container import-vpn-ribs {
        description
          "List of imported VPN RIBs configuration.";
        list import-vpn-rib {
          key "source-address-family nexthop-type";
          description
            "Configure imported VPN RIBs configuration.";
          leaf source-address-family {
            type import-vpn-rib-afi-type;
            description
              "Source address family type for imported RIBs.";
          }
          leaf nexthop-type {
            type import-rib-nhp-type;
            must "../nexthop-type='mpls'";
            description
              "Imported valid route.";
          }
          choice policy-type {
            description
              "Set route policy or filter.";
            case rtp-ref {
              description
                "Route policy.";
              leaf policy-name {
                type leafref {
                  path "/rtp:routing-policy/rtp:policy-definitions/rtp:policy-definition/rtp:name";
                }
                description
                  "Specify the policy applied to the routes imported from other address family.";
              }
            }
            case xpl-ref {
              description
                "Route filter.";
              leaf filter-name {
                type leafref {
                  path "/xpl:xpl/xpl:route-filters/xpl:route-filter/xpl:name";
                }
                description
                  "Specify a route-filter name.";
              }
              leaf filter-parameter {
                when "../filter-name";
                type xpl:filter-parameter-type;
                description
                  "Specify a route-filter parameter.";
              }
            }
          }
        }
      }
      uses bestroute-nh-relay-pri-grp;
      uses bgp:bestroute-nexthop-priority-grp;
      container interworkings {
        description
          "List of EVPN interworking tunnel enable configuration.";
        list interworking {
          key "tunnel-combination route-type";
          description
            "Configure EVPN interworking tunnel enable configuration.";
          leaf tunnel-combination {
            type tunnel-combination-type;
            description
              "Tunnel combination type for EVPN interworking tunnel.";
          }
          leaf route-type {
            type evpn-route-type;
            description
              "EVPN route type.";
          }
        }
      }
      container apply-sid-evpn-ribs {
        description
          "List of apply sid modes for EVPN RIB configuration.";
        list apply-sid-evpn-rib {
          key "encap-type route-type";
          description
            "Configure apply sid mode for EVPN RIB configuration.";
          leaf encap-type {
            type evpn-rib-encap-type;
            description
              "Encapsulation type of packets.";
          }
          leaf route-type {
            type evpn-route-type;
            description
              "EVPN route type.";
          }
          leaf mode {
            type apply-sid-mode-evpn-rib;
            mandatory true;
            description
              "Apply SID for EVPN RIB.";
          }
        }
      }
      container prefix-exempt {
        description
          "Configure the exempt filtering policy applied to the routes received when bgp memory-resilence occurred.";
        uses bgp:group-exempt-ip-prefix;
        uses bgp:group-exempt-ipv6-prefix;
      }
    }
  }
  augment "/ni:network-instance/ni:instances/ni:instance/bgp:bgp/bgp:base-process/bgp:afs/bgp:af/bgp:ipv4-unicast" {
    description
      "EVPN configuration.";
    container evpn {
      description
        "Configure EVPN IPv4.";
      container srv6 {
        when "../../../../../../../ni:name!='_public_'";
        description
          "Configure segment-routing IPv6 for EVPN.";
        leaf mode {
          type srv6-mode;
          description
            "SRv6 iteration mode.";
        }
        leaf down-switch {
          when "../mode='te'";
          type boolean;
          default "false";
          description
            "Enable/disable switch TE to BE if the associated TE tunnel goes down.";
        }
        leaf color-only {
          type empty;
          description
            "Enable SRv6-TE Policy color-only iteration.";
        }
        leaf track-bfd-for-locator {
          type empty;
          description
            "Enable SRv6-TE Policy track bfd-for-locator.";
        }
      }
      container common {
        when "../../../../../../../ni:name!='_public_'";
        description
          "Configure EVPN common attribute.";
        leaf reoriginate-disable {
          type boolean;
          default "false";
          description
            "Enable/disable reoriginate capability.";
        }
        leaf original-attributes {
          type empty;
          must "../reoriginate-disable='false'";
          description
            "Regenerate route with original attributes.";
        }
      }
      container local-cross {
        when "../../../../../../../ni:name!='_public_'";
        presence "Enable the EVPN instance to advertise routes to other VPN instances.";
        description
          "Configure EVPN local-cross attribute.";
        leaf remote-cross-route-enable {
          type boolean;
          default "false";
          description
            "Enable/disable the use of remotely leaked routes in EVPN local route leaking.";
        }
      }
      container irb-asymmetric {
        when "../../../../../../../ni:name!='_public_'";
        description
          "Configure IRB asymmetric mode.";
        uses irb-asymmetric-grp;
      }
    }
  }
  augment "/ni:network-instance/ni:instances/ni:instance/bgp:bgp/bgp:base-process/bgp:afs/bgp:af/bgp:ipv6-unicast" {
    description
      "EVPN configuration.";
    container evpn {
      description
        "Configure EVPN IPv6.";
      container srv6 {
        when "../../../../../../../ni:name!='_public_'";
        description
          "Configure segment-routing IPv6 for EVPN.";
        leaf mode {
          type srv6-mode;
          description
            "SRv6 iteration mode.";
        }
        leaf down-switch {
          when "../mode='te'";
          type boolean;
          default "false";
          description
            "Enable/disable switch TE to BE if the associated TE tunnel goes down.";
        }
        leaf color-only {
          type empty;
          description
            "Enable SRv6-TE Policy color-only iteration.";
        }
        leaf track-bfd-for-locator {
          type empty;
          description
            "Enable SRv6-TE Policy track bfd-for-locator.";
        }
      }
      container common {
        when "../../../../../../../ni:name!='_public_'";
        description
          "Configure EVPN common attribute.";
        leaf reoriginate-disable {
          type boolean;
          default "false";
          description
            "Enable/disable reoriginate capability.";
        }
        leaf original-attributes {
          type empty;
          must "../reoriginate-disable='false'";
          description
            "Regenerate route with original attributes.";
        }
      }
      container local-cross {
        when "../../../../../../../ni:name!='_public_'";
        presence "Enable the EVPN instance to advertise routes to other VPN instances.";
        description
          "Configure EVPN local-cross attribute.";
        leaf remote-cross-route-enable {
          type boolean;
          default "false";
          description
            "Enable/disable the use of remotely leaked routes in EVPN local route leaking.";
        }
      }
      container irb-asymmetric {
        when "../../../../../../../ni:name!='_public_'";
        description
          "Configure IRB asymmetric mode.";
        uses irb-asymmetric-grp;
      }
    }
  }
  augment "/bgp:bgp/bgp:base-process/bgp-rt:bgp-route" {
    description
      "BGP routes information of EVPN address family.";
    container l2vpn-evpn {
      config false;
      description
        "Statistics of BGP routes information of EVPN address family.";
      container statistics {
        description
          "List of BGP routes information of EVPN address family.";
        list statistic {
          must "./vpn-name = '_public_'";
          key "vpn-name";
          description
            "BGP EVPN address family routes statistics.";
          leaf vpn-name {
            type leafref {
              path "/ni:network-instance/ni:instances/ni:instance/ni:name";
            }
            description
              "VPN name of a BGP instance.";
          }
          leaf total-route-number {
            type uint32;
            description
              "Total number of EVPN routes.";
          }
          leaf ad-route-number {
            type uint32;
            description
              "Number of Ethernet Auto-Discovery routes.";
          }
          leaf mac-route-number {
            type uint32;
            description
              "Number of MAC/IP Advertisement routes.";
          }
          leaf include-route-number {
            type uint32;
            description
              "Number of Inclusive Multicast Ethernet Tag routes.";
          }
          leaf es-route-number {
            type uint32;
            description
              "Number of Ethernet Segment routes.";
          }
          leaf ip-prefix-route-number {
            type uint32;
            description
              "Number of IP Prefix routes.";
          }
          leaf smet-route-number {
            type uint32;
            description
              "Number of Selective Multicast Ethernet Tag routes.";
          }
          leaf igmp-join-route-number {
            type uint32;
            description
              "Number of IGMP Join Synch routes.";
          }
          leaf igmp-leave-route-number {
            type uint32;
            description
              "Number of IGMP Leave Synch routes.";
          }
        }
      }
      container ad-routes {
        config false;
        description
          "List of AD routes.";
        list ad-route {
          key "prefix route-distinguisher from route-type path-id";
          config false;
          description
            "Statistics of AD routes.";
          leaf prefix {
            type ad-prefix;
            description
              "AD route prefix.";
          }
          uses bgp-rt:routing-table-route-distinguisher;
          uses bgp-rt:routing-table-from;
          leaf route-type {
            type evpn-route-type-flag;
            description
              "Route type.";
          }
          uses bgp-rt:routing-table-path-id;
          uses evpn-prefix-sid-type;
          uses evpn-bypass-prefix-sid-type;
          leaf in-label {
            type uint32 {
              range "0..4294967295";
            }
            description
              "In-label.";
          }
          leaf out-label {
            type uint32 {
              range "0..4294967295";
            }
            description
              "Out-label.";
          }
          uses routing-table-type {
            description
              "Routing table information.";
          }
          uses relay-aigp-type;
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
          leaf rekey-counter {
            type uint32;
            description
              "Rekey counter when the Xsec is carried.";
          }
        }
      }
      container mac-routes {
        config false;
        description
          "List of MAC routes.";
        list mac-route {
          key "prefix route-distinguisher from route-type path-id";
          config false;
          description
            "Statistics of MAC routes.";
          leaf prefix {
            type mac-prefix;
            description
              "MAC route prefix.";
          }
          uses bgp-rt:routing-table-route-distinguisher;
          uses bgp-rt:routing-table-from;
          uses bgp-rt:routing-table-route-type;
          uses bgp-rt:routing-table-path-id;
          uses routing-table-type;
          uses relay-aigp-type;
          leaf in-label1 {
            type uint32 {
              range "0..4294967295";
            }
            description
              "Layer 2 incoming label.";
          }
          leaf in-label2 {
            type uint32 {
              range "0..4294967295";
            }
            description
              "Layer 3 incoming label.";
          }
          leaf out-label1 {
            type uint32 {
              range "0..4294967295";
            }
            description
              "Layer 2 outgoing label.";
          }
          leaf out-label2 {
            type uint32 {
              range "0..4294967295";
            }
            description
              "Layer 3 outgoing label.";
          }
          uses evpn-prefix-sid-type;
          uses evpn-bypass-prefix-sid-type;
          uses evpn-l3-prefix-sid-type;
          leaf effect-nexthop {
            type inet:ip-address-no-zone;
            description
              "Effective nexthop.";
          }
          leaf redirect-out-interface {
            type string {
              length "1..64";
            }
            description
              "Redirect out-interface.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container inclusive-routes {
        config false;
        description
          "List of inclusive routes.";
        list inclusive-route {
          key "prefix route-distinguisher from route-type path-id";
          config false;
          description
            "Statistics of inclusive routes.";
          leaf prefix {
            type inclusive-prefix;
            description
              "Inclusive route prefix.";
          }
          uses bgp-rt:routing-table-route-distinguisher;
          uses bgp-rt:routing-table-from;
          uses bgp-rt:routing-table-route-type;
          uses bgp-rt:routing-table-path-id;
          uses evpn-prefix-sid-type;
          leaf in-label {
            type uint32 {
              range "0..4294967295";
            }
            description
              "In-label.";
          }
          leaf out-label {
            type uint32 {
              range "0..4294967295";
            }
            description
              "Out-label.";
          }
          uses routing-table-type {
            description
              "Routing table information.";
          }
          uses relay-aigp-type;
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container es-routes {
        config false;
        description
          "List of ES routes.";
        list es-route {
          key "prefix route-distinguisher from route-type path-id";
          config false;
          description
            "Statistics of ES routes.";
          leaf prefix {
            type es-prefix;
            description
              "ES route prefix.";
          }
          uses bgp-rt:routing-table-route-distinguisher;
          uses bgp-rt:routing-table-from;
          uses bgp-rt:routing-table-route-type;
          uses bgp-rt:routing-table-path-id;
          uses routing-table-type {
            description
              "Routing table information.";
          }
          uses relay-aigp-type;
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container ip-prefix-routes {
        config false;
        description
          "List of IP Prefix routes.";
        list ip-prefix-route {
          key "prefix route-distinguisher from route-type path-id nexthop";
          config false;
          description
            "Statistics of IP Prefix routes.";
          leaf prefix {
            type evpn-ip-prefix;
            description
              "IP Prefix route prefix.";
          }
          uses bgp-rt:routing-table-route-distinguisher;
          uses bgp-rt:routing-table-from;
          uses bgp-rt:routing-table-route-type;
          uses bgp-rt:routing-table-path-id;
          uses routing-table-type;
          uses relay-aigp-type;
          leaf in-label {
            type uint32 {
              range "0..4294967295";
            }
            description
              "In-label.";
          }
          leaf out-label {
            type uint32 {
              range "0..4294967295";
            }
            description
              "Out-label.";
          }
          uses evpn-prefix-sid-type;
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-advertise-ad-routes {
        config false;
        description
          "List of advertised AD routes.";
        list peer-advertise-ad-route {
          key "remote-peer-address route-distinguisher prefix from route-type path-id";
          config false;
          description
            "Statistics of advertised AD routes.";
          leaf remote-peer-address {
            type inet:ip-address-no-zone;
            description
              "BGP neighbour address.";
          }
          uses bgp-rt:routing-table-route-distinguisher;
          leaf prefix {
            type ad-prefix;
            description
              "AD route prefix.";
          }
          uses bgp-rt:routing-table-from;
          leaf route-type {
            type evpn-route-type-flag;
            description
              "Route type.";
          }
          uses bgp-rt:routing-table-path-id;
          uses evpn-prefix-sid-type;
          uses evpn-bypass-prefix-sid-type;
          leaf in-label {
            type uint32 {
              range "0..4294967295";
            }
            description
              "In-label.";
          }
          leaf out-label {
            type uint32 {
              range "0..4294967295";
            }
            description
              "Out-label.";
          }
          uses routing-table-type-attrid;
          leaf effect-nexthop {
            type inet:ip-address-no-zone;
            description
              "Effective nexthop.";
          }
          leaf esi {
            type esi;
            description
              "ESI.";
          }
          uses routing-table-advertise-nexthop;
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
          leaf rekey-counter {
            type uint32;
            description
              "Rekey counter when the Xsec is carried.";
          }
        }
      }
      container peer-advertise-mac-routes {
        config false;
        description
          "List of advertised MAC routes.";
        list peer-advertise-mac-route {
          key "remote-peer-address route-distinguisher prefix from route-type path-id";
          config false;
          description
            "Statistics of advertised MAC routes.";
          leaf remote-peer-address {
            type inet:ip-address-no-zone;
            description
              "BGP neighbour address.";
          }
          uses bgp-rt:routing-table-route-distinguisher;
          leaf prefix {
            type mac-prefix;
            description
              "MAC route prefix.";
          }
          uses bgp-rt:routing-table-from;
          uses bgp-rt:routing-table-route-type;
          uses bgp-rt:routing-table-path-id;
          uses routing-table-type-attrid;
          leaf effect-nexthop {
            type inet:ip-address-no-zone;
            description
              "Effective nexthop.";
          }
          leaf in-label1 {
            type uint32 {
              range "0..4294967295";
            }
            description
              "Layer 2 incoming label.";
          }
          leaf in-label2 {
            type uint32 {
              range "0..4294967295";
            }
            description
              "Layer 3 incoming label.";
          }
          leaf out-label1 {
            type uint32 {
              range "0..4294967295";
            }
            description
              "Layer 2 outgoing label.";
          }
          leaf out-label2 {
            type uint32 {
              range "0..4294967295";
            }
            description
              "Layer 3 outgoing label.";
          }
          uses evpn-prefix-sid-type;
          uses evpn-bypass-prefix-sid-type;
          uses evpn-l3-prefix-sid-type;
          leaf esi {
            type esi;
            description
              "ESI.";
          }
          uses routing-table-advertise-nexthop;
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-advertise-inclusive-routes {
        config false;
        description
          "List of advertised inclusive routes.";
        list peer-advertise-inclusive-route {
          key "remote-peer-address route-distinguisher prefix from route-type path-id";
          config false;
          description
            "Statistics of advertised inclusive routes.";
          leaf remote-peer-address {
            type inet:ip-address-no-zone;
            description
              "BGP neighbour address.";
          }
          uses bgp-rt:routing-table-route-distinguisher;
          leaf prefix {
            type inclusive-prefix;
            description
              "Inclusive route prefix.";
          }
          uses bgp-rt:routing-table-from;
          uses bgp-rt:routing-table-route-type;
          uses bgp-rt:routing-table-path-id;
          uses evpn-prefix-sid-type;
          leaf in-label {
            type uint32 {
              range "0..4294967295";
            }
            description
              "In-label.";
          }
          leaf out-label {
            type uint32 {
              range "0..4294967295";
            }
            description
              "Out-label.";
          }
          uses routing-table-type-attrid;
          uses routing-table-advertise-nexthop;
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-advertise-es-routes {
        config false;
        description
          "List of advertised ES routes.";
        list peer-advertise-es-route {
          key "remote-peer-address route-distinguisher prefix from route-type path-id";
          config false;
          description
            "Statistics of advertised ES routes.";
          leaf remote-peer-address {
            type inet:ip-address-no-zone;
            description
              "BGP neighbour address.";
          }
          uses bgp-rt:routing-table-route-distinguisher;
          leaf prefix {
            type es-prefix;
            description
              "ES route prefix.";
          }
          uses bgp-rt:routing-table-from;
          uses bgp-rt:routing-table-route-type;
          uses bgp-rt:routing-table-path-id;
          uses routing-table-type-attrid;
          uses routing-table-advertise-nexthop;
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-advertise-ip-prefix-routes {
        config false;
        description
          "List of advertised IP Prefix routes.";
        list peer-advertise-ip-prefix-route {
          key "remote-peer-address route-distinguisher prefix from route-type path-id nexthop";
          config false;
          description
            "Statistics of advertised IP Prefix routes.";
          leaf remote-peer-address {
            type inet:ip-address-no-zone;
            description
              "BGP neighbour address.";
          }
          uses bgp-rt:routing-table-route-distinguisher;
          leaf prefix {
            type evpn-ip-prefix;
            description
              "IP Prefix route prefix.";
          }
          uses bgp-rt:routing-table-from;
          uses bgp-rt:routing-table-route-type;
          uses bgp-rt:routing-table-path-id;
          uses routing-table-type-attrid;
          leaf effect-nexthop {
            type inet:ip-address-no-zone;
            description
              "Effective nexthop.";
          }
          leaf in-label {
            type uint32 {
              range "0..4294967295";
            }
            description
              "In-label.";
          }
          leaf out-label {
            type uint32 {
              range "0..4294967295";
            }
            description
              "Out-label.";
          }
          uses evpn-prefix-sid-type;
          leaf gateway-ip {
            type inet:ip-address-no-zone;
            description
              "Gateway IP address.";
          }
          uses routing-table-advertise-nexthop;
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-receive-ad-routes {
        config false;
        description
          "List of received AD routes.";
        list peer-receive-ad-route {
          key "remote-peer-address route-distinguisher prefix from route-type path-id";
          config false;
          description
            "Statistics of received AD routes.";
          leaf remote-peer-address {
            type inet:ip-address-no-zone;
            description
              "BGP neighbour address.";
          }
          uses bgp-rt:routing-table-route-distinguisher;
          leaf prefix {
            type ad-prefix;
            description
              "AD route prefix.";
          }
          uses bgp-rt:routing-table-from;
          leaf route-type {
            type evpn-route-type-flag;
            description
              "Route type.";
          }
          uses bgp-rt:routing-table-path-id;
          uses evpn-prefix-sid-type;
          uses evpn-bypass-prefix-sid-type;
          leaf in-label {
            type uint32 {
              range "0..4294967295";
            }
            description
              "In-label.";
          }
          leaf out-label {
            type uint32 {
              range "0..4294967295";
            }
            description
              "Out-label.";
          }
          uses routing-table-type-attrid;
          leaf effect-nexthop {
            type inet:ip-address-no-zone;
            description
              "Effective nexthop.";
          }
          leaf esi {
            type esi;
            description
              "ESI.";
          }
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
          leaf rekey-counter {
            type uint32;
            description
              "Rekey counter when the Xsec is carried.";
          }
        }
      }
      container peer-receive-mac-routes {
        config false;
        description
          "List of received MAC routes.";
        list peer-receive-mac-route {
          key "remote-peer-address route-distinguisher prefix from route-type path-id";
          config false;
          description
            "Statistics of received MAC routes.";
          leaf remote-peer-address {
            type inet:ip-address-no-zone;
            description
              "BGP neighbour address.";
          }
          uses bgp-rt:routing-table-route-distinguisher;
          leaf prefix {
            type mac-prefix;
            description
              "MAC route prefix.";
          }
          uses bgp-rt:routing-table-from;
          uses bgp-rt:routing-table-route-type;
          uses bgp-rt:routing-table-path-id;
          uses routing-table-type-attrid;
          leaf effect-nexthop {
            type inet:ip-address-no-zone;
            description
              "Effective nexthop.";
          }
          leaf in-label1 {
            type uint32 {
              range "0..4294967295";
            }
            description
              "Layer 2 incoming label.";
          }
          leaf in-label2 {
            type uint32 {
              range "0..4294967295";
            }
            description
              "Layer 3 incoming label.";
          }
          leaf out-label1 {
            type uint32 {
              range "0..4294967295";
            }
            description
              "Layer 2 outgoing label.";
          }
          leaf out-label2 {
            type uint32 {
              range "0..4294967295";
            }
            description
              "Layer 3 outgoing label.";
          }
          uses evpn-prefix-sid-type;
          uses evpn-bypass-prefix-sid-type;
          uses evpn-l3-prefix-sid-type;
          leaf esi {
            type esi;
            description
              "ESI.";
          }
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-receive-inclusive-routes {
        config false;
        description
          "List of received inclusive routes.";
        list peer-receive-inclusive-route {
          key "remote-peer-address route-distinguisher prefix from route-type path-id";
          config false;
          description
            "Statistics of received inclusive routes.";
          leaf remote-peer-address {
            type inet:ip-address-no-zone;
            description
              "BGP neighbour address.";
          }
          uses bgp-rt:routing-table-route-distinguisher;
          leaf prefix {
            type inclusive-prefix;
            description
              "Inclusive route prefix.";
          }
          uses bgp-rt:routing-table-from;
          uses bgp-rt:routing-table-route-type;
          uses bgp-rt:routing-table-path-id;
          uses evpn-prefix-sid-type;
          leaf in-label {
            type uint32 {
              range "0..4294967295";
            }
            description
              "In-label.";
          }
          leaf out-label {
            type uint32 {
              range "0..4294967295";
            }
            description
              "Out-label.";
          }
          uses routing-table-type-attrid;
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-receive-es-routes {
        config false;
        description
          "List of received ES routes.";
        list peer-receive-es-route {
          key "remote-peer-address route-distinguisher prefix from route-type path-id";
          config false;
          description
            "Statistics of received ES routes.";
          leaf remote-peer-address {
            type inet:ip-address-no-zone;
            description
              "BGP neighbour address.";
          }
          uses bgp-rt:routing-table-route-distinguisher;
          leaf prefix {
            type es-prefix;
            description
              "ES route prefix.";
          }
          uses bgp-rt:routing-table-from;
          uses bgp-rt:routing-table-route-type;
          uses bgp-rt:routing-table-path-id;
          uses routing-table-type-attrid;
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container peer-receive-ip-prefix-routes {
        config false;
        description
          "List of received IP Prefix routes.";
        list peer-receive-ip-prefix-route {
          key "remote-peer-address route-distinguisher prefix from route-type path-id nexthop";
          config false;
          description
            "Statistics of received IP Prefix routes.";
          leaf remote-peer-address {
            type inet:ip-address-no-zone;
            description
              "BGP neighbour address.";
          }
          uses bgp-rt:routing-table-route-distinguisher;
          leaf prefix {
            type evpn-ip-prefix;
            description
              "IP Prefix route prefix.";
          }
          uses bgp-rt:routing-table-from;
          uses bgp-rt:routing-table-route-type;
          uses bgp-rt:routing-table-path-id;
          uses routing-table-type-attrid;
          leaf effect-nexthop {
            type inet:ip-address-no-zone;
            description
              "Effective nexthop.";
          }
          leaf in-label {
            type uint32 {
              range "0..4294967295";
            }
            description
              "In-label.";
          }
          leaf out-label {
            type uint32 {
              range "0..4294967295";
            }
            description
              "Out-label.";
          }
          uses evpn-prefix-sid-type;
          leaf gateway-ip {
            type inet:ip-address-no-zone;
            description
              "Gateway IP address.";
          }
          leaf preferred-value {
            type uint32 {
              range "0..4294967295";
            }
            description
              "Preferred value of a protocol.";
          }
          leaf preference {
            type uint8 {
              range "0..255";
            }
            description
              "Preference of a route.";
          }
          leaf attribute-index {
            type leafref {
              path "/bgp:bgp/bgp:base-process/bgp-rt:bgp-route/bgp-evpn:l2vpn-evpn/bgp-evpn:attributes/bgp-evpn:attribute/bgp-evpn:index";
            }
            description
              "The ID of attribute.";
          }
        }
      }
      container attributes {
        description
          "List of attributes of BGP EVPN routes.";
        list attribute {
          key "vpn-name index";
          description
            "BGP EVPN routes attributes state.";
          uses bgp-rt:routing-table-vpn-name;
          leaf index {
            type uint32;
            description
              "BGP EVPN route attribute id.";
          }
          leaf origin {
            type bgp-rt:bgp-origin-type;
            description
              "The attributes of Origin.";
          }
          leaf med {
            type uint32;
            description
              "Route MED.The attribute is only fit for the routes from EBGP peer, not suit for which of IBGP peer.";
          }
          leaf local-preference {
            type uint32;
            description
              "Local priority. The attribute is only fit for the routes from IBGP peer, not suit for which of EBGP peer.";
          }
          leaf aggregator-as {
            type string {
              length "1..11";
            }
            description
              "AS number of the route summarizer.";
          }
          leaf aggregator-id {
            type inet:ip-address-no-zone;
            description
              "ID of the route summarizer.";
          }
          leaf originator {
            type inet:ip-address-no-zone;
            description
              "Router ID of the route initiator.";
          }
        }
      }
    }
  }
  augment "/ni:network-instance/ni:instances/ni:instance/bgp:bgp/bgp:instance-processs/bgp:instance-process/bgp:afs/bgp:af" {
    description
      "Augment for an L2VPN instance and EVPN association.";
    container l2vpn-evpn {
      when "(../bgp:type = 'evpn') and (../../../../../../ni:name='_public_')";
      description
        "Configure L2VPN-EVPN.";
      leaf policy-vpntarget {
        type boolean;
        default "true";
        description
          "Enable/disable VPN target-based filtering for the received VPN routes. By default, VPN target-based filtering is enabled. Only the VPN route whose Export RT attribute matches the local Import RT attribute can be added to the routing table. This option can be used in the inter-AS VPN Option B solution and the ASBR MP-EBGP inter-AS L2VPN solution in Kompella mode.";
      }
      leaf add-path-select-num {
        type uint8 {
          range "2..128";
        }
        description
          "Number of add-path routes.";
      }
      leaf reflect-between-client {
        type boolean;
        default "true";
        description
          "Enable/disable route reflection between clients. If clients of a route reflector (RR) are fully meshed, you can disable route reflection among clients to reduce the cost.";
      }
      leaf reflect-df-election-extcommunity-compatible {
        type boolean;
        default "false";
        description
          "Enable/disable reflect only one df-election extcommunity to peer.";
      }
      choice reflector-type {
        description
          "Set IPv4 address or id.";
        case address {
          description
            "IPv4 address.";
          leaf reflector-cluster-ipv4 {
            type inet:ipv4-address-no-zone;
            description
              "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
        case id {
          description
            "Set value.";
          leaf reflector-cluster-id {
            type uint32 {
              range "1..4294967295";
            }
            description
              "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
      }
      container nexthop-recursive-lookup {
        description
          "Configure next hop iteration.";
        uses bgp:nexthop-recursive-lookup-delay;
      }
      uses bgp:vrf-af-dampening-routes;
      uses bgp:slow-peer-type;
      container prefix-exempt {
        description
          "Configure the exempt filtering policy applied to the routes received when bgp memory-resilence occurred.";
        uses bgp:group-exempt-ip-prefix;
        uses bgp:group-exempt-ipv6-prefix;
      }
    }
  }
  augment "/ni:network-instance/ni:instances/ni:instance/bgp:bgp/bgp:base-process/bgp:afs/bgp:af/bgp:ipv4-vpn" {
    description
      "EVPN configuration.";
    container evpn {
      description
        "Configure the EVPN configurations.";
      container import-evpn-ribs {
        description
          "List of imported EVPN RIBs configuration.";
        list import-evpn-rib {
          key "nexthop-type route-type";
          description
            "Configure imported EVPN RIBs configuration.";
          leaf nexthop-type {
            type import-rib-nhp-type;
            must "../nexthop-type='srv6'";
            description
              "Nexthop relay type.";
          }
          leaf route-type {
            type evpn-route-type;
            description
              "Import route type.";
          }
          choice policy-type {
            description
              "Set route policy or filter.";
            case rtp-ref {
              description
                "Route policy.";
              leaf policy-name {
                type leafref {
                  path "/rtp:routing-policy/rtp:policy-definitions/rtp:policy-definition/rtp:name";
                }
                description
                  "Specify the policy applied to the routes imported from other address family.";
              }
            }
            case xpl-ref {
              description
                "Route filter.";
              leaf filter-name {
                type leafref {
                  path "/xpl:xpl/xpl:route-filters/xpl:route-filter/xpl:name";
                }
                description
                  "Specify a route-filter name.";
              }
              leaf filter-parameter {
                when "../filter-name";
                type xpl:filter-parameter-type;
                description
                  "Specify a route-filter parameter.";
              }
            }
          }
        }
      }
      container load-balancing {
        when "../import-evpn-ribs";
        description
          "Configure the number of imported rib routes.";
        leaf maximum-load-balancing-import-rib {
          type uint16 {
            range "1..2";
          }
          default "1";
          description
            "Specify the maximum number of imported rib routes.";
        }
      }
    }
  }
  augment "/ni:network-instance/ni:instances/ni:instance/bgp:bgp/bgp:base-process/bgp:afs/bgp:af/bgp:ipv6-vpn" {
    description
      "EVPN configuration.";
    container evpn {
      description
        "Configure the EVPN configurations.";
      container import-evpn-ribs {
        description
          "List of imported EVPN RIBs configuration.";
        list import-evpn-rib {
          key "nexthop-type route-type";
          description
            "Configure imported EVPN RIBs configuration.";
          leaf nexthop-type {
            type import-rib-nhp-type;
            must "../nexthop-type='srv6'";
            description
              "Nexthop relay type.";
          }
          leaf route-type {
            type evpn-route-type;
            description
              "Import route type.";
          }
          choice policy-type {
            description
              "Set route policy or filter.";
            case rtp-ref {
              description
                "Route policy.";
              leaf policy-name {
                type leafref {
                  path "/rtp:routing-policy/rtp:policy-definitions/rtp:policy-definition/rtp:name";
                }
                description
                  "Specify the policy applied to the routes imported from other address family.";
              }
            }
            case xpl-ref {
              description
                "Route filter.";
              leaf filter-name {
                type leafref {
                  path "/xpl:xpl/xpl:route-filters/xpl:route-filter/xpl:name";
                }
                description
                  "Specify a route-filter name.";
              }
              leaf filter-parameter {
                when "../filter-name";
                type xpl:filter-parameter-type;
                description
                  "Specify a route-filter parameter.";
              }
            }
          }
        }
      }
      container load-balancing {
        when "../import-evpn-ribs";
        description
          "Configure the number of imported rib routes.";
        leaf maximum-load-balancing-import-rib {
          type uint16 {
            range "1..2";
          }
          default "1";
          description
            "Specify the maximum number of imported rib routes.";
        }
      }
    }
  }
  augment "/ni:network-instance/ni:instances/ni:instance/bgp:bgp/bgp:instance-processs/bgp:instance-process/bgp:peers/bgp:peer/bgp:afs/bgp:af" {
    description
      "Augment for an L2VPN instance and EVPN association.";
    container l2vpn-evpn {
      when "../bgp:type = 'evpn' and ../../../../../../../../ni:name='_public_'";
      must "(mac-route-limit='true' and route-limit) or mac-route-limit='false'";
      must "not(advertise-arp = 'true' and advertise-irb = 'true')";
      must "not(advertise-nd = 'true' and advertise-irbv6 = 'true')";
      description
        "Configure peer EVPN.";
      leaf group-name {
       
        type leafref {
          path "../../../../../../bgp:peer-groups/bgp:peer-group/bgp:name";
        }
        must "(../../../../../../bgp:peer-groups/bgp:peer-group[bgp:name=current()]/bgp:type = 'ibgp' and ../../../../bgp:remote-as = /bgp:bgp/bgp:instance-processs/bgp:instance-process[bgp:name = current()/../../../../../../bgp:name]/bgp:as-number) or (../../../../../../bgp:peer-groups/bgp:peer-group[bgp:name=current()]/bgp:type = 'ebgp' and ../../../../bgp:remote-as != /bgp:bgp/bgp:instance-processs/bgp:instance-process[bgp:name = current()/../../../../../../bgp:name]/bgp:as-number)";
        must "../../../../../../bgp:peer-groups/bgp:peer-group[bgp:name=current()]/bgp:afs/bgp:af[bgp:type='evpn']";
        must "../../../../../../bgp:peer-groups/bgp:peer-group[bgp:name=current()]/bgp:peer-establish-mode='static'";
        description
          "Configure a name for a peer group. By default, BGP peers join no peer group. BGP peers distinguish the peer group type when joining a peer group. IBGP peers cannot join an EBGP peer group. After a peer is deleted from the peer group, the peer is disabled from the address family. The object cannot be modified.";
      }
      leaf allow-as-loop {
        type uint8 {
          range "1..10";
        }
        description
          "Allow repetitive local AS numbers. By default, repetitive local AS numbers are not allowed.";
      }
      leaf reflect-client {
        when "../../../../bgp:remote-as = /bgp:bgp/bgp:instance-processs/bgp:instance-process[bgp:name = current()/../../../../../../bgp:name]/bgp:as-number";
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      uses policy-type-grp;
      leaf advertise-community {
        type boolean;
        default "false";
        description
          "Enable/disable advertise community attribute to a peer or peer group.";
      }
      leaf advertise-large-community {
        type config-type;
        default "default";
        description
          "Enable large-community attribute advertisement. By default, the function is not configured on any peer. The Link-state address family and the RPD address family do not support this element.";
      }
      uses advertise-grp;
      leaf advertise-add-path-mode {
        type add-path-cap-type;
        description
          "Enable add-path route advertisement to a peer.";
      }
      leaf advertise-add-path-num {
        type uint8 {
          range "2..128";
        }
        description
          "Number of add-path routes that can be advertised to a peer.";
      }
      leaf mac-route-limit {
        type boolean;
        default "false";
        description
          "Enable/disable MAC routing overflow alarm received from the specified peer.";
      }
      leaf route-limit {
        when "../mac-route-limit='true'";
        type uint32 {
          range "1..4294967295";
        }
        description
          "Configure the maximum number of routes that can be accepted from a peer.";
      }
      leaf route-limit-percent {
        when "../route-limit";
        type uint8 {
          range "1..100";
        }
        default "75";
        description
          "Specify the percentage of routes when a router starts to generate an alarm.";
      }
      leaf route-limit-type {
        when "../route-limit";
        type route-limit-type;
        must "(../route-limit-type = 'idle-timeout' and ../route-limit-idle-timeout) or (../route-limit-type = 'alert-only') or (../route-limit-type = 'idle-forever') or (../route-limit-type = 'noparameter')";
        default "noparameter";
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        when "../route-limit-type = 'idle-timeout'";
        type uint16 {
          range "1..1200";
        }
        units "min";
        description
          "Enable/disable specify the value of the idle-timeout timer to automatically reestablish the connections after they are cut off when the number of routes exceeds the set threshold.";
      }
      leaf route-update-interval {
       
        type uint16 {
          range "0..600";
        }
        units "s";
        description
          "Specify the minimum interval at which Update packets are sent. By default, the interval at which Update packets are sent to IBGP peers is 15s, and the interval at which Update packets are sent to EBGP peers is 30s.";
      }
      leaf reoriginate-route-enable {
        type boolean;
        default "false";
        description
          "Enable/disable route regeneration.";
      }
      uses reoriginated-route-grp;
      leaf split-group-name {
        type string {
          length "1..31";
        }
        description
          "Split group name.";
      }
      leaf next-hop-mode {
        type evpn-next-hop-mode;
        default "null";
        description
          "Enable next hop mode.";
      }
      leaf high-priority {
        type peer-comm-config-type;
        default "default";
        description
          "Enable a higher priority to a specified peer.";
      }
      leaf preferred-value {
        type uint32 {
          range "0..65535";
        }
        default "0";
        description
          "Assign a preferred value for the routes learned from a specified peer. The value is an integer. After a preferred value is configured for the routes learned from a specified peer, all the routes that learnt from this peer will use this preferred value. When multiple routes reach the same address prefix, the route with the largest preferred value will be selected.";
      }
      leaf peer-as-check {
        type bgp:peer-attr-enable-type;
        description
          "Enable/disable BGP to prevents the routes received from an EBGP peer from being broadcast to other peers with the same AS number.";
      }
      leaf transit-med-to-ebgp {
        type bgp:peer-attr-enable-type;
        description
          "Transmits the MED attribute to EBGP peers.";
      }
      leaf graceful-restart-static-timer {
        type uint32 {
          range "3600..2147483647";
        }
        units "s";
        description
          "Specifies the maximum time during which a peer waits for a BGP session reestablishment.";
      }
      leaf reoriginate-vpnv4-route {
        type boolean;
        default "false";
        description
          "Enable/disable VPNv4 route regeneration and advertisement.";
      }
      leaf reoriginate-vpnv6-route {
        type boolean;
        default "false";
        description
          "Enable/disable reoriginating the route of VPNv6.";
      }
      container effect-state {
        config false;
        description
          "Operational state of peer.";
        leaf transit-med-to-ebgp {
          type boolean;
          description
            "Transmits the MED attribute to EBGP peers.";
        }
      }
      uses bgp:path-attr-map-type;
      container option {
        description
          "Configure bgp evpn multi instances peer extended options.";
        leaf unique-source-ip-prefix {
          type bgp:peer-attr-enable-type;
          description
            "Enable the unique source function.";
        }
      }
    }
  }
  augment "/ni:network-instance/ni:instances/ni:instance/bgp:bgp/bgp:instance-processs/bgp:instance-process/bgp:peer-groups/bgp:peer-group/bgp:afs/bgp:af" {
    description
      "Augment for an L2VPN instance and EVPN association.";
    container l2vpn-evpn {
      when "../bgp:type = 'evpn' and ../../../../../../../../ni:name='_public_'";
      must "(mac-route-limit='true' and route-limit) or mac-route-limit='false'";
      must "not(advertise-arp = 'true' and advertise-irb = 'true')";
      must "not(advertise-nd = 'true' and advertise-irbv6 = 'true')";
      description
        "Configure EVPN peer group.";
      leaf allow-as-loop {
        type uint8 {
          range "1..10";
        }
        description
          "Allow repetitive local AS numbers. By default, repetitive local AS numbers are not allowed.";
      }
      leaf reflect-client {
        when "../../../../bgp:type = 'ibgp'";
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      uses policy-type-grp;
      leaf split-group-name {
        type string {
          length "1..31";
        }
        description
          "Split group name.";
      }
      leaf next-hop-mode {
        type evpn-next-hop-mode;
        default "null";
        description
          "Enable next hop mode.";
      }
      leaf high-priority {
        type boolean;
        default "false";
        description
          "Enable/disable routes received from a specified peer have a higher priority.";
      }
      leaf advertise-community {
        type boolean;
        default "false";
        description
          "Enable/disable an advertise the community attribute to a peer or peer group.";
      }
      leaf advertise-large-community {
        type boolean;
        default "false";
        description
          "Enable/disable large-community attribute advertisement. The Link-state address family and the RPD address family do not support this element.";
      }
      uses advertise-grp;
      leaf advertise-add-path-mode {
        type add-path-cap-type;
        description
          "Enable add-path route advertisement to a peer.";
      }
      leaf advertise-add-path-num {
        type uint8 {
          range "2..128";
        }
        description
          "Number of add-path routes that can be advertised to a peer group.";
      }
      leaf mac-route-limit {
        type boolean;
        default "false";
        description
          "Enable/disable MAC routing overflow alarm received from the specified peer.";
      }
      leaf route-limit {
        when "(../mac-route-limit='true')";
        type uint32 {
          range "1..4294967295";
        }
        description
          "Configure the maximum number of routes that can be accepted from a peer.";
      }
      leaf route-limit-percent {
        when "../route-limit";
        type uint8 {
          range "1..100";
        }
        default "75";
        description
          "Specify the percentage of routes when a router starts to generate an alarm.";
      }
      leaf route-limit-type {
        when "../route-limit";
        type route-limit-type;
        must "(../route-limit-type = 'idle-timeout' and ../route-limit-idle-timeout) or (../route-limit-type = 'alert-only') or (../route-limit-type = 'idle-forever') or (../route-limit-type = 'noparameter')";
        default "noparameter";
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        when "../route-limit-type = 'idle-timeout'";
        type uint16 {
          range "1..1200";
        }
        units "min";
        description
          "Specify the value of the idle-timeout timer to automatically reestablish the connections after they are cut off when the number of routes exceeds the set threshold.";
      }
      leaf route-update-interval {
       
        type uint16 {
          range "0..600";
        }
        units "s";
        description
          "Specify the minimum interval at which Update packets are sent. By default, the interval at which Update packets are sent to IBGP peers is 15s, and the interval at which Update packets are sent to EBGP peers is 30s.";
      }
      leaf reoriginated-route-enable {
        type boolean;
        default "false";
        description
          "Enable/disable route regeneration.";
      }
      uses reoriginated-route-grp;
      leaf preferred-value {
        type uint32 {
          range "0..65535";
        }
        default "0";
        description
          "Assign a preferred value for the routes learned from a specified peer. The value is an integer. After a preferred value is configured for the routes learned from a specified peer, all the routes that learnt from this peer will use this preferred value. When multiple routes reach the same address prefix, the route with the largest preferred value will be selected.";
      }
      leaf transit-med-to-ebgp {
        when "../../../../bgp:type = 'ebgp'";
        type boolean;
        default "false";
        description
          "Enable/disable transmits the MED attribute to EBGP peers.";
      }
      leaf peer-as-check {
        when "../../../../bgp:type='ebgp'";
        type bgp:peer-attr-enable-type;
        default "disable";
        description
          "Enable/disable BGP to prevents the routes received from an EBGP peer from being broadcast to other peers with the same AS number.";
      }
      leaf reoriginated-vpnv4-route {
        type boolean;
        default "false";
        description
          "Enable/disable VPNv4 route regeneration and advertisement.";
      }
      leaf reoriginated-vpnv6-route {
        type boolean;
        default "false";
        description
          "Enable/disable reoriginating the route of VPNv6.";
      }
      container option {
        description
          "Configure bgp evpn multi instances group extended options.";
        leaf unique-source-ip-prefix {
          type empty;
          description
            "Enable the unique source function.";
        }
      }
    }
  }
  augment "/ni:network-instance/ni:instances/ni:instance/bgp:bgp/bgp:instance-processs/bgp:instance-process/bgp:afs/bgp:af/bgp:ipv4-unicast" {
    description
      "EVPN configuration.";
    container evpn {
      description
        "Configure EVPN IPv4.";
      container irb-asymmetric {
        when "../../../../../../../../ni:name!='_public_'";
        description
          "Configure IRB asymmetric mode.";
        uses irb-asymmetric-grp;
      }
    }
  }
  augment "/ni:network-instance/ni:instances/ni:instance/bgp:bgp/bgp:instance-processs/bgp:instance-process/bgp:afs/bgp:af/bgp:ipv6-unicast" {
    description
      "EVPN configuration.";
    container evpn {
      description
        "Configure EVPN IPv6.";
      container irb-asymmetric {
        when "../../../../../../../../ni:name!='_public_'";
        description
          "Configure IRB asymmetric mode.";
        uses irb-asymmetric-grp;
      }
    }
  }

  rpc reset-base-process-bgp-evpn-slow-delete-sid {
   
    description
      "Reset slow-delete sids of BGP EVPN.";
  }

  rpc reset-base-process-bgp-evpn-af-slow-delete-sid {
   
    description
      "Reset slow-delete sids of L3EVPN.";

    input {
      leaf address-family {
        type slow-delete-sid-af-type;
        mandatory true;
        description
          "Address family type of a BGP instance.";
      }
    }
  }
}
