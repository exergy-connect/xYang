module bbf-xpon-traffic-descriptor-profile {
  yang-version 1.1;
  namespace "urn:bbf:yang:bbf-xpon-traffic-descriptor-profile";
  prefix traffic-desc-profile;

  import bbf-xpongemtcont {
    prefix bbf-xpongemtcont;
  }

  organization
    "Broadband Forum <https://www.broadband-forum.org>
     Common YANG Work Area.";
  contact
    "Comments or questions about this Broadband Forum YANG module
     should be directed to <mailto:info@broadband-forum.org>.

     Editor: XinWen Yao, Huawei";
  description
    "This module contains traffic descriptor profile config data.";

  revision 2025-11-13 {
    description
      "Modify must condition validate.";
    reference
      "ITU-T G.984, G.988, G.9807, G.987, G.989,SFF 8472,SFF 8077";
  }
  revision 2024-03-20 {
    description
      "Initial revision.";
    reference
      "ITU-T G.984, G.988, G.9807, G.987, G.989,SFF 8472,SFF 8077";
  }

  grouping traffic-descriptor-profile-config-data {
    description
      "Config data for traffic descriptor profile.";
    leaf frequency-type {
      type enumeration {
        enum "calculate-period" {
          value 0;
          description
            "The final effective assignment frequency type depends
             on the bandwidth assignment mode of the port.
             If the min-loop-delay mode is used, the assignment frequency type is 2 bursts per frame.
             If the max-bandwidth-usage mode is used, the assignment frequency type is 8 bursts per frame.";
        }
        enum "single-frame" {
          value 1;
          description
            "The assignment frequency type is single burst per frame.";
        }
        enum "two-burst-per-frame" {
          value 2;
          description
            "The assignment frequency type is 2 bursts per frame.";
        }
        enum "four-burst-per-frame" {
          value 3;
          description
            "The assignment frequency type is 4 bursts per frame.";
        }
        enum "eight-burst-per-frame" {
          value 4;
          description
            "The assignment frequency type is 8 bursts per frame.";
        }
        enum "sixteen-burst-per-frame" {
          value 5;
          description
            "The assignment frequency type is 16 bursts per frame.";
        }
        enum "thirty-two-burst-per-frame" {
          value 6;
          description
            "The assignment frequency type is 32 bursts per frame.";
        }
      }
      default "single-frame";
      description
        "The assignment frequency type of the traffic descriptor profile.";
    }
    leaf fix-delay {
      type boolean;
      must
        "boolean(../bbf-xpongemtcont:fixed-bandwidth) and
         (../bbf-xpongemtcont:assured-bandwidth = 0) and
         boolean(../bbf-xpongemtcont:maximum-bandwidth) and
         '(../bbf-xpongemtcont:maximum-bandwidth) = (../bbf-xpongemtcont:fixed-bandwidth)'" {
        error-message
          "When fix-delay is configured, fixed-bandwidth must be equal to maximum-bandwidth.";
      }
      description
        "Indicates the fixed delay.
         This parameter can minimize the jitter of the fixed-bandwidth services.
         Enabling this parameter consumes more bandwidth resources.";
    }
    leaf bandwidth-compensate {
      type boolean;
      must
        "boolean(../bbf-xpongemtcont:fixed-bandwidth) and
         (../bbf-xpongemtcont:assured-bandwidth = 0) and
         boolean(../bbf-xpongemtcont:maximum-bandwidth) and
         ((../bbf-xpongemtcont:maximum-bandwidth) = (../bbf-xpongemtcont:fixed-bandwidth))" {
        error-message
          "When bandwidth-compensate is configured, fixed-bandwidth must be equal to maximum-bandwidth.";
      }
      description
        "Indicates the bandwidth compensation.
         When the actual bandwidth cannot meet the fixed bandwidth requirements
         due to certain causes, expand the bandwidth in the transmission process.";
    }
  }

  augment "/bbf-xpongemtcont:xpongemtcont/bbf-xpongemtcont:traffic-descriptor-profiles/bbf-xpongemtcont:traffic-descriptor-profile" {
    description
      "Traffic descriptor profile config data.";
    uses traffic-descriptor-profile-config-data;
  }
}
