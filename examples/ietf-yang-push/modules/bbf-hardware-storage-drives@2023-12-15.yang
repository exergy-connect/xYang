module bbf-hardware-storage-drives {
  yang-version 1.1;
  namespace "urn:bbf:yang:bbf-hardware-storage-drives";
  prefix bbf-hw-strg-drv;

  import iana-hardware {
    prefix ianahw;
  }
  import ietf-hardware {
    prefix hw;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on hardware
     management as applicable to access network equipment. As such,
     this module is specific to access network equipment (e.g.,
     BBF-specified Access Nodes and FTTdp DPUs).

     Specifically, this module augments the ietf-hardware model with
     the management of hardware components with data storage
     capability as their main functionality, e.g., hard disk drive
     (HDD), solid-state device (SSD), solid-state hybrid drive (SSHD),
     object storage device (OSD), or other.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }

  augment "/hw:hardware/hw:component" {
    when "derived-from-or-self (hw:class, \"ianahw:storage-drive\")" {
      description
        "Data nodes for hardware components of class
         'storage-drive'.";
    }
    description
      "Data nodes for hardware components of class 'storage-drive'.";
    container storage-drive {
      config false;
      description
        "Storage drive data nodes.

         A storage drive is a hardware component with data storage
         capability as its main functionality, e.g., hard disk drive
         (HDD), solid-state device (SSD), solid-state hybrid drive
         (SSHD), object storage device (OSD), or other.";
      leaf device-transfer-rate {
        type decimal64 {
          fraction-digits 2;
        }
        units "transfers per second";
        description
          "The I/O requests that were transferred to/from the storage
           drive.";
      }
      leaf device-data-read-rate {
        type uint64;
        units "bytes per second";
        description
          "The amount of data read from the device expressed in number
           of bytes per second.";
      }
      leaf device-data-write-rate {
        type uint64;
        units "bytes per second";
        description
          "The amount of data written to the device expressed in
           number of bytes per second.";
      }
      leaf device-data-read {
        type uint64;
        units "kilobytes";
        description
          "The total number of kilobytes read.";
      }
      leaf device-data-write {
        type uint64;
        units "kilobytes";
        description
          "The total number of kilobytes written.";
      }
    }
  }
}
