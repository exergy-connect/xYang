module huawei-nvo3 {
  namespace "urn:huawei:yang:huawei-nvo3";
  prefix nvo3;

  import huawei-bd {
    prefix bd;
  }
  import huawei-ifm {
    prefix ifm;
  }
  import huawei-network-instance {
    prefix ni;
  }
  import huawei-pub-type {
    prefix pub-type;
  }
  import ietf-inet-types {
    prefix inet;
  }
  import huawei-extension {
    prefix ext;
  }
  import huawei-evpl {
    prefix evpl;
  }
  import huawei-l3vpn {
    prefix l3vpn;
  }

  organization
    "Huawei Technologies Co., Ltd.";
  contact
    "Huawei Industrial Base
     Bantian, Longgang
     Shenzhen 518129
     People's Republic of China
     Website: http://www.huawei.com
     Email: support@huawei.com";
  description
    "Management for data center network virtualization over Layer 3.";

  revision 2025-08-13 {
    description
      "Add nodes for VPN VXLAN.";
    reference
      "Huawei private.";
  }
  revision 2024-04-29 {
    description
      "Add keys for VXLAN VPN peer.";
    reference
      "Huawei private.";
  }
  revision 2024-04-22 {
    description
      "Add leaf for VXLAN packet fragment.";
    reference
      "Huawei private.";
  }
  revision 2024-04-10 {
    description
      "Add nodes for VPN VXLAN.";
    reference
      "Huawei private.";
  }
  revision 2024-02-20 {
    description
      "Add ignore PIP bypass.";
    reference
      "Huawei private.";
  }
  revision 2024-01-27 {
    description
      "Move the must condition from the nvo3 container to its list node.";
    reference
      "Huawei private.";
  }
  revision 2024-01-26 {
    description
      "Add leaf vxlan-id.";
    reference
      "Huawei private.";
  }
  revision 2024-01-10 {
    description
      "Add evpl-peer.";
    reference
      "Huawei private.";
  }
  revision 2023-11-23 {
    description
      "Add unique-source leaf.";
    reference
      "Huawei private.";
  }
  revision 2023-08-09 {
    description
      "Modify the range of EVPL instance ID and service ID.";
    reference
      "Huawei private.";
  }
  revision 2023-02-02 {
    description
      "Add container bd-members.";
    reference
      "Huawei private.";
  }
  revision 2022-06-17 {
    description
      "Modify container pip.";
    reference
      "Huawei private.";
  }
  revision 2021-08-12 {
    description
      "Modify the description of leaf source-vtep-ip.";
    reference
      "Huawei private.";
  }
  revision 2020-03-06 {
    description
      "The modifications in the schema file are synchronized to the YANG file.";
    reference
      "Huawei private.";
  }
  revision 2019-03-01 {
    description
      "Initial revision.";
    reference
      "Huawei private.";
  }

 

  typedef vni-state {
    type enumeration {
      enum "down" {
        value 0;
        description
          "The state is down.";
      }
      enum "up" {
        value 1;
        description
          "The state is up.";
      }
    }
    description
      "The state for VNI.";
  }

  typedef tunnel-type {
    type enumeration {
      enum "dynamic" {
        value 0;
        description
          "Learning via protocols.";
      }
      enum "static" {
        value 1;
        description
          "Created by users.";
      }
    }
    description
      "VXLAN tunnel type.";
  }

  typedef tunnel-mode {
    type enumeration {
      enum "default-mode" {
        value 0;
        description
          "Default mode.";
      }
      enum "cu-mode" {
        value 1;
        description
          "Control-User separation mode.";
      }
    }
    description
      "VXLAN tunnel mode.";
  }

  typedef peer-learning-type {
    type enumeration {
      enum "peer" {
        value 1;
        description
          "Learning peers for multicast via BGP.";
      }
      enum "evpl-peer" {
        value 2;
        description
          "Learning EVPL peers for multicast via BGP.";
      }
    }
    description
      "The type of peer Learning via BGP.";
  }

  typedef preference-type {
    type enumeration {
      enum "primary" {
        value 1;
        description
          "Primary enable.";
      }
      enum "secondary" {
        value 2;
        description
          "Secondary enable.";
      }
      enum "bypass" {
        value 4;
        description
          "Bypass enable.";
      }
    }
    description
      "Preference type.";
  }

  typedef ipv6-preference-type {
    type enumeration {
      enum "primary" {
        value 1;
        description
          "Primary enable.";
      }
      enum "secondary" {
        value 2;
        description
          "Secondary enable.";
      }
    }
    description
      "Preference type.";
  }

  typedef nqa-state-type {
    type enumeration {
      enum "unknown" {
        value 0;
        description
          "The NQA state is unknown.";
      }
      enum "down" {
        value 1;
        description
          "The NQA state is down.";
      }
      enum "up" {
        value 2;
        description
          "The NQA state is up.";
      }
    }
    description
      "The NQA state.";
  }

  container nvo3 {
    description
      "Management of NVO3.";
    container vni-instances {
      description
        "List of virtual extensible local area network.";
      list vni-instance {
        key "vni source-nve";
        description
          "Configure the information of virtual extensible local area network.";
        leaf vni {
          type uint32 {
            range "1..16777215";
          }
          description
            "VXLAN network identifier.";
        }
        leaf source-nve {
          type leafref {
            path "/ifm:ifm/ifm:interfaces/ifm:interface/ifm:name";
          }
          must "/ifm:ifm/ifm:interfaces/ifm:interface[ifm:name=current()]/ifm:type='Nve'";
          description
            "The name of interface NVE, as VXLAN tunnel source point.";
        }
        leaf state {
          type vni-state;
          config false;
          description
            "The state of the VNI. When the VTEP address in the VNI is reachable, the state is up, the opposite is down.";
        }
        leaf protocol-bgp {
          type peer-learning-type;
          description
            "Learning VTEPs via BGP for communication in a same VNI.";
        }
        container static-peers {
          description
            "List of VTEPs created by users for multicast in a same VNI.";
          list static-peer {
            key "address";
            description
              "Configure VTEP by users for multicast.";
            leaf address {
              type inet:ipv4-address-no-zone;
              description
                "The address of VTEP.";
            }
            leaf vxlan-id {
              type uint32 {
                range "1000..2000";
              }
              description
                "VXLAN tunnel identifier.";
            }
          }
        }
        container static-ipv6-peers {
          description
            "List of VTEPs created by users for multicast in a same VNI.";
          list static-ipv6-peer {
            key "address";
            description
              "Configure VTEP by users for multicast.";
            leaf address {
              type inet:ipv6-address-no-zone;
              description
                "The IPv6 address of VTEP.";
            }
          }
        }
        container static-evpl-peers {
          description
            "List of VTEPs created by users for ethernet virtual private line in the same VNI.";
          list static-evpl-peer {
            key "address";
            max-elements 1;
            description
              "Configure VTEP by users for ethernet virtual private line.";
            leaf address {
              type inet:ipv4-address-no-zone;
              must "(not(../../../static-peers/static-peer) and not(../../../protocol-bgp)) or not(../address)";
              description
                "The address of VTEP.";
            }
            leaf preference {
             
              type preference-type;
              default "primary";
              description
                "The preference of VXLAN tunnel.";
            }
          }
        }
        container static-evpl-ipv6-peers {
          description
            "List of IPv6 VTEPs created by users for ethernet virtual private line in the same VNI.";
          list static-evpl-ipv6-peer {
            key "address";
            max-elements 1;
            description
              "Configure IPv6 VTEP by users for ethernet virtual private line.";
            leaf address {
              type inet:ipv6-address-no-zone;
              description
                "The IPv6 address of VTEP.";
            }
            leaf preference {
             
              type ipv6-preference-type;
              default "primary";
              description
                "The preference of VXLAN6 tunnel.";
            }
          }
        }
        container static-vpn-tunnels {
          description
            "List of tunnels created by users for VPN VXLAN in a same VNI.";
          list static-vpn-tunnel {
            must "./source != ./peer";
            key "source peer vpn-instance-name";
            description
              "Configure a VPN VXLAN tunnel.";
            leaf source {
              type inet:ipv4-address-no-zone;
              description
                "The source address of the VPN VXLAN tunnel.";
            }
            leaf peer {
              type inet:ipv4-address-no-zone;
              description
                "The destination address of the VPN VXLAN tunnel.";
            }
            leaf vpn-instance-name {
              type leafref {
                path "/ni:network-instance/ni:instances/ni:instance/ni:name";
              }
              must "/ni:network-instance/ni:instances/ni:instance[ni:name=current()]/l3vpn:afs/l3vpn:af[l3vpn:type='ipv4-unicast']";
              description
                "Name of the VPN instance bound to the VPN VXLAN.";
            }
          }
        }
        container static-vpn-ipv6-tunnels {
          description
            "List of tunnels created by users for VPN VXLAN in a same VNI.";
          list static-vpn-ipv6-tunnel {
            must "./source != ./peer";
            key "source peer vpn-instance-name";
            description
              "Configure a VPN VXLAN tunnel.";
            leaf source {
              type inet:ipv6-address-no-zone;
              description
                "The source address of the VPN VXLAN tunnel.";
            }
            leaf peer {
              type inet:ipv6-address-no-zone;
              description
                "The destination address of the VPN VXLAN tunnel.";
            }
            leaf vpn-instance-name {
              type leafref {
                path "/ni:network-instance/ni:instances/ni:instance/ni:name";
              }
              must "/ni:network-instance/ni:instances/ni:instance[ni:name=current()]/l3vpn:afs/l3vpn:af[l3vpn:type='ipv6-unicast']";
              description
                "Name of the VPN instance bound to the VPN VXLAN.";
            }
          }
        }
        container mcast-groups {
          description
            "List of VTEPs created by users for mcast group in a same VNI.";
          list mcast-group {
            key "address";
            max-elements 1;
            description
              "Configure VTEP by users for mcast group.";
            leaf address {
              type inet:ipv4-address-no-zone;
              description
                "The address of VTEP.";
            }
          }
        }
        container flood-peers {
          description
            "List of flood peers created by users.";
          list flood-peer {
            key "address";
            description
              "Configure flood peer.";
            leaf address {
              type inet:ipv4-address-no-zone;
              description
                "The address of peer.";
            }
          }
        }
      }
    }
    container vni-labels {
      description
        "List of VXLAN network identifiers.";
      list vni-label {
        key "vni";
        description
          "Configure VXLAN network identifier.";
        leaf vni {
          type uint32 {
            range "1..16777215";
          }
          description
            "VXLAN network identifier.";
        }
        container peers {
          description
            "List of peer address.";
          list peer {
            key "peer-address";
            description
              "Configure peer address.";
            leaf peer-address {
              type inet:ipv4-address-no-zone;
              description
                "The address of remote peer.";
            }
            leaf description {
              type string {
                length "1..64";
              }
              description
                "Description of remote peer.";
            }
          }
        }
      }
    }
    container vteps {
      config false;
      description
        "Statistics of VTEPs.";
      container peers {
        config false;
        description
          "List of VTEPs for multicast in a same VNI.";
        list peer {
          key "vni source destination";
          config false;
          description
            "Operational data of VTEPs for multicast with the same VNI.";
          leaf vni {
            type uint32 {
              range "1..16777215";
            }
            config false;
            description
              "VXLAN network identifier.";
          }
          leaf source {
            type inet:ip-address-no-zone;
            config false;
            description
              "The address of VXLAN tunnel source point.";
          }
          leaf destination {
            type inet:ip-address-no-zone;
            config false;
            description
              "The address of VTEP.";
          }
          leaf type {
            type tunnel-type;
            config false;
            description
              "The type of VXLAN tunnel.";
          }
          leaf out-vni {
            type uint32 {
              range "1..16777215";
            }
            config false;
            description
              "VXLAN network identifier for mapping.";
          }
        }
      }
      container evpl-peers {
        config false;
        description
          "List of VTEPs for ethernet virtual private line in a same VNI.";
        list evpl-peer {
          key "id";
          description
            "Operational data of VTEPs for Ethernet virtual private lines with the same VNI.";
          leaf id {
            type uint32 {
              range "1..4294967295";
            }
            description
              "The identification of the EVPL instance.";
          }
          leaf vni {
            type uint32 {
              range "1..16777215";
            }
            description
              "Local VNI for communication.";
          }
          leaf source {
            type inet:ip-address-no-zone;
            description
              "The address of VXLAN tunnel source point.";
          }
          leaf ipv6-source {
            type inet:ipv6-address-no-zone;
            description
              "The IPv6 address of VXLAN tunnel source point.";
          }
          leaf peer {
            type inet:ip-address-no-zone;
            description
              "The address of primary VTEP.";
          }
          leaf out-vni {
            type uint32 {
              range "1..16777215";
            }
            description
              "Primary VNI for mapping.";
          }
          leaf backup-peer {
            type inet:ip-address-no-zone;
            description
              "The address of backup VTEP.";
          }
          leaf backup-out-vni {
            type uint32 {
              range "1..16777215";
            }
            description
              "Backup VNI for mapping.";
          }
          leaf bypass-peer {
            type inet:ip-address-no-zone;
            description
              "The address of bypass VTEP.";
          }
          leaf bypass-out-vni {
            type uint32 {
              range "1..16777215";
            }
            description
              "Bypass VNI for mapping.";
          }
        }
      }
      container cu-peers {
        config false;
        description
          "List of VNI Peers Table of CU Mode.";
        list cu-peer {
          key "vni source destination";
          description
            "Operational data of VNI Peer Table of CU Mode.";
          leaf vni {
            type uint32 {
              range "1..16777215";
            }
            description
              "The identification of VXLAN tunnel.";
          }
          leaf source {
            type inet:ip-address-no-zone;
            description
              "The address of VXLAN tunnel source point.";
          }
          leaf destination {
            type inet:ip-address-no-zone;
            description
              "The address of VTEP.";
          }
          leaf type {
            type tunnel-type;
            description
              "VXLAN tunnel type.";
          }
          leaf out-vni {
            type uint32 {
              range "1..16777215";
            }
            description
              "VXLAN network identifier for mapping.";
          }
          leaf nqa-state {
            type nqa-state-type;
            description
              "The NQA state:unknown, down or up.";
          }
          leaf packet-loss-ratio {
            type uint8 {
              range "0..100";
            }
            units "%";
            description
              "The NQA packet loss ratio.";
          }
        }
      }
      container vpn-peers {
        config false;
        description
          "List of VNI peers of VPN tunnels.";
        list vpn-peer {
          key "vni source destination";
          config false;
          description
            "Operational data of VNI peers of VPN tunnels.";
          leaf vni {
            type uint32 {
              range "1..16777215";
            }
            description
              "The identification of VXLAN tunnel.";
          }
          leaf source {
            type inet:ip-address-no-zone;
            description
              "The source address of VXLAN tunnel.";
          }
          leaf destination {
            type inet:ip-address-no-zone;
            description
              "The destination address of vlxan tunnel.";
          }
          leaf type {
            type tunnel-type;
            description
              "The type of VXLAN tunnel.";
          }
          leaf out-vni {
            type uint32 {
              range "1..16777215";
            }
            description
              "VXLAN network identifier for mapping.";
          }
        }
      }
    }
    container global-attribute {
      description
        "Configure global attribute of VXLAN.";
      leaf exact-sub-enable {
        type boolean;
        default "false";
        description
          "Enable/disable exact route subscribe.";
      }
      leaf ignore-pip-bypass {
        type boolean;
        must "(../ignore-pip-bypass='true' and ../exact-sub-enable='true') or (../ignore-pip-bypass='false')";
        default "false";
        description
          "Enable/disable ignore PIP bypass.";
      }
      leaf packet-fragment {
        type boolean;
        default "true";
        description
          "Enable/disable VXLAN packet fragment.";
      }
      leaf tunnel-mac-import {
        type boolean;
        default "false";
        description
          "Enable/disable tunnel MAC import.";
      }
    }
    container tunnels {
      config false;
      description
        "List of VXLAN tunnel information.";
      list tunnel {
        key "id";
        config false;
        description
          "Statistics of VXLAN tunnels.";
        leaf id {
          type uint32 {
            range "1..4294967295";
          }
          config false;
          description
            "The identification of VXLAN tunnel.";
        }
        leaf source {
         
          type inet:ip-address-no-zone;
          config false;
          description
            "The address of VXLAN tunnel source point.";
        }
        leaf destination {
         
          type inet:ip-address-no-zone;
          config false;
          description
            "The address of VTEP.";
        }
        leaf mode {
         
          type tunnel-mode;
          config false;
          description
            "VXLAN tunnel mode.";
        }
        leaf state {
          type vni-state;
          config false;
          description
            "VXLAN tunnel state. When the address of VTEP is reachable, the state is up, otherwise is down.";
        }
        leaf type {
          type tunnel-type;
          config false;
          description
            "VXLAN tunnel type.";
        }
        leaf up-time {
          type string {
            length "1..10";
          }
          config false;
          description
            "The continuous time as VXLAN tunnel is reachable.";
        }
        leaf vpn-name {
         
          type string {
            length "1..31";
          }
          description
            "VPN instance name.";
        }
      }
    }
    container bd-members {
      config false;
      description
        "List of BD member corresponding to the VNI.";
      list bd-member {
        key "vni";
        config false;
        description
          "Operational data of BD member corresponding to the VNI.";
        leaf vni {
          type uint32;
          description
            "VXLAN network identifier.";
        }
        leaf bd-id {
          type uint32;
          description
            "The bridge domain corresponding to the VXLAN network.";
        }
        leaf state {
          type vni-state;
          description
            "The state of the VNI.";
        }
      }
    }
  }

  augment "/ifm:ifm/ifm:interfaces/ifm:interface" {
    description
      "The NVO3 configuration for interface.";
    container nve {
      when "../ifm:type='Nve'";
      description
        "Configure NVO3 for interface NVE.";
      container attribute {
        must "(./source-vtep-ip and ./bypass-vtep-ip and ./source-vtep-ip != ./bypass-vtep-ip) or not(./source-vtep-ip) or not(./bypass-vtep-ip)";
        must "(./source-vtep-ipv6 and ./bypass-vtep-ipv6 and ./source-vtep-ipv6 != ./bypass-vtep-ipv6) or not(./source-vtep-ipv6) or not(./bypass-vtep-ipv6)";
        description
          "Configure VTEPs for interface NVE.";
        leaf source-vtep-ip {
          type inet:ipv4-address-no-zone;
          description
            "The address of interface NVE, as VXLAN tunnel source point.";
        }
        leaf source-vtep-ipv6 {
          type inet:ipv6-address-no-zone;
          description
            "The IPv6 address of interface NVE, as VXLAN tunnel source point.";
        }
        leaf phys-address {
          type pub-type:mac-address;
          description
            "The interface's address at its protocol sub-layer. For example, for an 802.x interface, this object normally contains a Media Access Control (MAC) address.";
        }
        leaf bypass-vtep-ip {
          type inet:ipv4-address-no-zone;
          description
            "The address of interface NVE, as source point in bypass VXLAN tunnel.";
        }
        leaf bypass-vtep-ipv6 {
          type inet:ipv6-address-no-zone;
          description
            "The IPv6 address of interface NVE, as source point in bypass VXLAN tunnel.";
        }
        leaf unique-vtep-ip {
          type inet:ipv4-address-no-zone;
          description
            "The address of interface NVE, as source point in unique VXLAN tunnel.";
        }
        leaf unique-vtep-ipv6 {
          type inet:ipv6-address-no-zone;
          description
            "The IPv6 address of interface NVE, as source point in unique VXLAN tunnel.";
        }
      }
      container pip {
        must "((./source-ip and ./peer-ip) and (./source-ip != ./peer-ip) and not(../pip-ipv6)) or (not(./source-ip) and not(./peer-ip))";
        presence "pip bypass IP";
        description
          "Configure primary IP address as bypass VXLAN tunnel.";
        leaf source-ip {
          type inet:ipv4-address-no-zone;
          must "(../../attribute[source-vtep-ip != current()])";
          mandatory true;
          description
            "The address of interface NVE, as VXLAN tunnel source point.";
        }
        leaf peer-ip {
          type inet:ipv4-address-no-zone;
          must "(../../attribute[source-vtep-ip != current()])";
          mandatory true;
          description
            "The address of interface NVE, as VXLAN tunnel peer point.";
        }
      }
      container pip-ipv6 {
        must "((./source-ipv6 and ./peer-ipv6) and (./source-ipv6 != ./peer-ipv6) and not(../pip)) or (not(./source-ipv6) and not(./peer-ipv6))";
        presence "pip bypass IPv6";
        description
          "Configure primary IPv6 address as bypass VXLAN tunnel.";
        leaf source-ipv6 {
          type inet:ipv6-address-no-zone;
          must "(../../attribute[source-vtep-ipv6 != current()])";
          mandatory true;
          description
            "The IPv6 address of interface NVE, as VXLAN tunnel source point.";
        }
        leaf peer-ipv6 {
          type inet:ipv6-address-no-zone;
          must "(../../attribute[source-vtep-ipv6 != current()])";
          mandatory true;
          description
            "The IPv6 address of interface NVE, as VXLAN tunnel peer point.";
        }
      }
    }
    container nvo3-gateway {
      when "../ifm:type='Vbdif'";
      description
        "Configure anycast gateway features for NVO3.";
      leaf vxlan-anycast-gateway {
        type boolean;
        default "false";
        description
          "Enable/disable VXLAN anycast gateway features.";
      }
      leaf common-anycast-gateway {
        type boolean;
        default "false";
        description
          "Enable/disable common anycast gateway features.";
      }
    }
  }
  augment "/bd:bd/bd:instances/bd:instance" {
    description
      "The NVO3 configuration for bridge domains.";
    container nvo3 {
      description
        "Configure NVO3 for a BD.";
      list vni-list {
        must "../../bd:mac-learn-style!='qualify'";
        key "vni";
        max-elements 1;
        description
          "Configure the list of VNI that a bridge domain corresponds.";
        leaf vni {
          type uint32 {
            range "1..16777215";
          }
          description
            "VXLAN network identifier.";
        }
        leaf split-horizon {
          type boolean;
          default "false";
          description
            "Enable/disable split horizon mode.";
        }
        leaf source-vtep-ip {
          type inet:ipv4-address-no-zone;
          description
            "The address of VXLAN tunnel source point. When not configured, the address of interface NVE is used as default.";
        }
      }
      container map-vnis {
        description
          "List of Map VNI in a same BD.";
        list map-vni {
          key "vni";
          max-elements 1;
          description
            "Configure the list of VNI that a bridge domain corresponds.";
          leaf vni {
            type uint32 {
              range "1..16777215";
            }
            description
              "VXLAN network identifier.";
          }
          leaf split-group {
            type string {
              length "1..31";
            }
            mandatory true;
            description
              "Split group name.";
          }
        }
      }
    }
  }
  augment "/ni:network-instance/ni:instances/ni:instance" {
    description
      "The NVO3 configuration for network instances.";
    container nvo3 {
      when "../ni:name != '_public_'";
      description
        "Configure NVO3 for a network instance.";
      list vni-list {
        key "vni";
        max-elements 1;
        description
          "Configure NVO3 for a network instance.";
        leaf vni {
          type uint32 {
            range "1..16777215";
          }
          description
            "VXLAN network identifier.";
        }
        leaf source-vtep-ip {
          type inet:ipv4-address-no-zone;
          description
            "The address of VXLAN tunnel source point. When not configured, the address of interface NVE is used as default.";
        }
      }
    }
  }
  augment "/evpl:evpl/evpl:instances/evpl:instance" {
    when "./evpl:mode = 'vxlan-mode'";
    description
      "The NVO3 configuration for EVPL instances.";
    container nvo3 {
      description
        "Configure NVO3 for an EVPL instance.";
      container attribute {
        description
          "Configure the attribute for an EVPL instance in VXLAN mode.";
        leaf vtep-ip {
          type inet:ipv4-address-no-zone;
          description
            "The address of VXLAN tunnel source point. When not configured, the address of interface NVE is used as default.";
        }
      }
      container vni-lists {
        description
          "List of VXLAN network identifiers.";
        list vni-list {
          key "vni";
          max-elements 1;
          description
            "Configure a VNI list for an EVPL instance in VXLAN mode.";
          leaf vni {
            type uint32 {
              range "1..16777215";
            }
            description
              "VXLAN network identifier.";
          }
        }
      }
    }
  }
  augment "/bd:bd/bd:profiles/bd:profile" {
    description
      "The NVO3 configuration for bridge domain profile.";
    container nvo3 {
      description
        "Configure NVO3 for a BD profile.";
      leaf vni-auto {
        type boolean;
        default "false";
        description
          "Enable/disable VNI automatic allocation.";
      }
    }
  }
}
