module bbf-xpon-onu-authentication-features {
  yang-version 1.1;
  namespace "urn:bbf:yang:bbf-xpon-onu-authentication-features";
  prefix bbf-xpon-onu-authf;

  organization
    "Broadband Forum <https://www.broadband-forum.org>
     Fiber Access Networks Work Area";
  contact
    "Comments or questions about this Broadband Forum YANG module
     should be directed to <mailto:info@broadband-forum.org>.

     Editor:      Robert Peschi, Nokia

     Editor:      Kevin Noll, Vecima

     PS Leader:   Joey Boyd, Adtran

     WA Director: Marta Seda, Calix";
  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).

     Specifically, this module defines features used for Optical
     Network Unit (ONU) authentication and the decision to apply
     an OMCI function.

     Copyright (c) 2018-2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-385; see
     the WT itself for full legal notices.";

  revision 2024-10-04 {
    description
      "TBD
       * Approval Date:    TBD.
       * Publication Date: TBD.";
    reference
      "TBD";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }

  feature support-onu-authentication-report {
    description
      "Indicates support for an action reporting the results of
       Optical Network Unit (ONU) authentication by the Management
       Plane.";
  }

  feature can-retrieve-onu-eqpt-id-hw-and-sw-version-pre-auth {
    description
      "Indicates that the OLT is capable to retrieve the equipment
       ID, the hardware version and the software version from an ONU
       before the ONU is already authenticated.

       Note that this feature has to be understood in the strict
       sense: when supported this feature does not necessary imply
       that the OLT is capable to (fully) manage an ONU with an
       embedded OMCI function (eOMCI).";
  }

  feature can-retrieve-loid-pre-auth {
    description
      "Indicates that the OLT is capable to retrieve the ONU Logical
       Identifier (LOID) from an ONU before the ONU is already
       authenticated. Note that this feature has to be understood in
       the strict sense: when supported this feature does not
       necessary imply that the OLT is capable to (fully) manage an
       ONU with an embedded OMCI function (eOMCI).";
  }

  feature configurable-onu-name {
    description
      "Indicates support for configuring an 'onu-name' at a virtual
       Access Network Interface (vANI).";
  }

  feature configurable-expected-onu-management-mode {
    description
      "Indicates support for configuring an
       'expected-onu-management-mode' at a virtual Access Network
       Interface (vANI).";
  }
}
