module bbf-xpon-tr069-common {
  yang-version 1.1;
  namespace "urn:bbf:yang:bbf-xpon-tr069-common";
  prefix bbf-xpon-tr069c;

  import ietf-inet-types {
    prefix inet;
  }
  import bbf-yang-types {
    prefix bbf-yang;
  }
  import iana-crypt-hash {
    prefix ianach;
  }

  organization
    "Broadband Forum <https://www.broadband-forum.org>
     Fiber Access Networks Work Area";
  contact
    "Comments or questions about this Broadband Forum YANG module
     should be directed to <mailto:info@broadband-forum.org>.

     Editor:      Robert Peschi, Nokia

     PS Leader:   Joey Boyd, Adtran

     WA Director: Marta Seda, Calix";
  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).

     Specifically, this module defines the TR-069 management server.

     Copyright (c) 2018-2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-385; see
     the WT itself for full legal notices.";

  revision 2024-09-27 {
    description
      "TBD.
       * Approval Date:    TBD.
       * Publication Date: TBD.";
    reference
      "TBD.";
  }

  feature bbf-xpon-tr069-management-server {
    description
      "Indicates support for Optical Network Unit (ONU) TR-069
       management server.";
    reference
      "ITU-T G.988 Clause 9.12.16";
  }

  grouping ani-tr069-server-prof-data {
    description
      "ONU-side configuration data for Optical Network Unit (ONU)
       TR-069 management server.";
    list tr069-management-server-profile {
      key "name";
      description
        "Optical Network Unit (ONU) TR-069 management server
         configuration parameters.";
      reference
        "ITU-T G.988 Clause 9.12.3;
         ITU-T G.988 Clause 9.12.4;
         ITU-T G.988 Clause 9.12.16";
      leaf name {
        type bbf-yang:string-ascii64;
        description
          "TR-069 management server profile name.";
      }
      leaf url {
        type inet:uri {
          length "0..375";
        }
        mandatory true;
        description
          "TR-069 management server URL.";
        reference
          "ITU-T G.988 Clause 9.12.3;
           ITU-T G.988 Clause 9.12.16";
      }
      leaf username {
        type bbf-yang:string-ascii64;
        mandatory true;
        description
          "TR-069 management server authentication username.";
        reference
          "ITU-T G.988 Clause 9.12.3;
           ITU-T G.988 Clause 9.12.4;
           ITU-T G.988 Clause 9.12.16";
      }
      leaf password {
        type ianach:crypt-hash;
        mandatory true;
        description
          "TR-069 management server authentication password.";
        reference
          "ITU-T G.988 Clause 9.12.3;
           ITU-T G.988 Clause 9.12.4;
           ITU-T G.988 Clause 9.12.16";
      }
      leaf validation-scheme {
        type enumeration {
          enum "disabled" {
            description
              "Disable validation.";
          }
          enum "md5-digest-authentication" {
            description
              "Validate using MD5 digest authentication.";
            reference
              "RFC 2617 Section 3";
          }
          enum "basic-authentication" {
            description
              "Validate using basic authentication.";
            reference
              "RFC 2617 Section 2";
          }
        }
        mandatory true;
        description
          "The validation scheme used when the ONU validates a
           challenge.";
        reference
          "ITU-T G.988 Clause 9.12.4;
           RFC 2617 Section 2;
           RFC 2617 Section 3";
      }
      leaf realm {
        when "../validation-scheme = 'md5-digest-authentication'";
        type string {
          length "0..25";
        }
        mandatory true;
        description
          "Indicates the realm of the TR-069 management server
           in user digest authentication. This string is to be
           displayed to users so they know which username and
           password to use, ref to RFC 2617, Section 3 for details.";
        reference
          "ITU-T G.988 Clause 9.12.3;
           ITU-T G.988 Clause 9.12.4;
           ITU-T G.988 Clause 9.12.16
           RFC 2617 Section 3.2.1";
      }
    }
  }
}
