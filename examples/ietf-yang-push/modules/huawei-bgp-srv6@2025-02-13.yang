module huawei-bgp-srv6 {
  yang-version 1;
  namespace "urn:huawei:yang:huawei-bgp-srv6";
  prefix bgp-srv6;

  import huawei-network-instance {
    prefix ni;
  }
  import huawei-extension {
    prefix ext;
  }
  import ietf-inet-types {
    prefix inet;
  }
  import huawei-bgp {
    prefix bgp;
  }
  import huawei-srv6 {
    prefix srv6;
  }
  import huawei-srpolicy {
    prefix srpolicy;
  }

  organization
    "Huawei Technologies Co., Ltd.";
  contact
    "Huawei Industrial Base
     Bantian, Longgang
     Shenzhen 518129
     People's Republic of China
     Website: http://www.huawei.com
     Email: support@huawei.com";
  description
    "BGP SRv6 configuration.";

  revision 2025-02-13 {
    description
      "Modify service SID type leaf.";
    reference
      "Huawei private.";
  }
  revision 2022-12-05 {
    description
      "Modify must position.";
    reference
      "Huawei private.";
  }
  revision 2020-02-25 {
    description
      "The YANG descriptions are modified according to new standards.";
    reference
      "Huawei private.";
  }
  revision 2020-01-22 {
    description
      "The modifications in the code are synchronized to the YANG file.";
    reference
      "Huawei private.";
  }
  revision 2019-03-22 {
    description
      "Initial revision.";
    reference
      "Huawei private.";
  }

 

  typedef apply-sid-mode {
    type enumeration {
      enum "per-instance" {
        value 0;
        description
          "Allocate a SID per VPN instance.";
      }
      enum "per-nexthop" {
        value 1;
        description
          "Allocate a SID per next hop.";
      }
    }
    description
      "SID allocation mode of SRv6 for BGP.";
  }

  typedef sid-compress-type {
    type enumeration {
      enum "common" {
        value 0;
        description
          "Not Support sid compress.";
      }
      enum "compress" {
        value 1;
        description
          "Support sid compress.";
      }
    }
    description
      "Sid mode type.";
  }

  typedef sid-flavor {
    type enumeration {
      enum "coc-next" {
        value 1;
        description
          "SID flavor (coc, next).";
      }
      enum "next" {
        value 2;
        description
          "SID flavor (next).";
      }
    }
    description
      "Sid mode type.";
  }

  typedef service-sid-type {
    type enumeration {
      enum "unicast" {
        value 0;
        description
          "Unicast service SID.";
      }
      enum "anycast" {
        value 2;
        description
          "Anycast service SID.";
      }
    }
    description
      "L3VPN service SID type.";
  }

  grouping tunnel-info-ipv4 {
    description
      "Display the information of the vrf IPv4 which used by this tunnel.";
    container tunnel-vpnv4-infos {
      config false;
      description
        "List of VPN instances. All VPN IPv4 instances which use this tunnel.";
      list tunnel-vpnv4-info {
        key "vrf-name nexthop";
        description
          "Statistics of a VPN IPv4 instance of this Tunnel.";
        leaf vrf-name {
          type leafref {
            path "/ni:network-instance/ni:instances/ni:instance/ni:name";
          }
          description
            "VPN name of a BGP instance.";
        }
        leaf nexthop {
          type inet:ipv6-address-no-zone;
          description
            "The next hop address used by this tunnel.";
        }
      }
    }
  }

  grouping tunnel-info-ipv6 {
    description
      "Display the information of the vrf IPv6 which used by this tunnel.";
    container tunnel-vpnv6-infos {
      config false;
      description
        "List of VPN instances. All VPN IPv6 instances which use this tunnel.";
      list tunnel-vpnv6-info {
        key "vrf-name nexthop";
        description
          "Statistics of a VPN IPv6 instance of this Tunnel.";
        leaf vrf-name {
          type leafref {
            path "/ni:network-instance/ni:instances/ni:instance/ni:name";
          }
          description
            "VPN name of a BGP instance.";
        }
        leaf nexthop {
          type inet:ipv6-address-no-zone;
          description
            "The next hop IPv6 address used by this tunnel.";
        }
      }
    }
  }

  augment "/ni:network-instance/ni:instances/ni:instance/bgp:bgp/bgp:base-process" {
    description
      "BGP SRv6 configuration.";
    container locator {
      description
        "Configure BGP segment-routing IPv6 locator.";
      leaf name {
        type leafref {
          path "/ni:network-instance/ni:instances/ni:instance/srv6:srv6/srv6:locators/srv6:locator/srv6:name";
        }
        must "not (../../bgp:afs/bgp:af/bgp:ipv4-unicast/bgp-srv6:locators/bgp-srv6:locator[bgp-srv6:name=current()] or ../../bgp:afs/bgp:af/bgp:ipv6-unicast/bgp-srv6:locators/bgp-srv6:locator[bgp-srv6:name=current()])";
        must "not (../../bgp:afs/bgp:af/bgp:ipv4-unicast/bgp-srv6:locators/bgp-srv6:locator[bgp-srv6:service-sid-type='unicast'] or ../../bgp:afs/bgp:af/bgp:ipv6-unicast/bgp-srv6:locators/bgp-srv6:locator[bgp-srv6:service-sid-type='unicast'])";
        description
          "Locator name.";
      }
      leaf advertise-sbfd-discriminator {
        when "../name";
        type empty;
        description
          "Enable SRv6 SBFD reflector discriminator in BGP.";
      }
      leaf apply-sid-compress-type {
        when "../name";
        type sid-compress-type;
        must ".='common' or /ni:network-instance/ni:instances/ni:instance[ni:name='_public_']/srv6:srv6/srv6:locators/srv6:locator[srv6:name=current()/../name]/srv6:compress-16";
        must "(.='common' and not(../apply-sid-flavor)) or .='compress'";
        must "not(../apply-sid-flavor) or (../apply-sid-flavor and /ni:network-instance/ni:instances/ni:instance[ni:name='_public_']/srv6:srv6/srv6:compress-16-mode and ((../apply-sid-flavor='coc-next' and /ni:network-instance/ni:instances/ni:instance[ni:name='_public_']/srv6:srv6/srv6:compress-16-mode='default') or ../apply-sid-flavor!='coc-next'))";
        default "common";
        description
          "Configure SID compress type.";
      }
      leaf-list apply-sid-flavor {
        when "../apply-sid-compress-type!='common'";
        type sid-flavor;
        max-elements 1;
        description
          "Configure SID flavor.";
      }
    }
  }
  augment "/ni:network-instance/ni:instances/ni:instance/bgp:bgp/bgp:base-process/bgp:afs/bgp:af/bgp:ipv4-unicast" {
    description
      "BGP SRv6 configuration.";
    container locators {
      description
        "List of locators used by segment-routing IPv6 for BGP.";
      list locator {
        key "name";
        unique "service-sid-type";
        max-elements 2;
        description
          "Configure SRv6 locator.";
        leaf name {
          type leafref {
            path "/ni:network-instance/ni:instances/ni:instance/srv6:srv6/srv6:locators/srv6:locator/srv6:name";
          }
          description
            "Locator name.";
        }
        leaf auto-sid {
          when "../../../../../../../../ni:name!='_public_' and ../apply-sid-compress-type='common'";
          type boolean;
          default "true";
          description
            "Enable/disable SID automatic allocation ability.";
        }
        leaf apply-sid-mode {
          when "../../../../../../../../ni:name='_public_'";
          type apply-sid-mode;
          must ". != 'per-nexthop' or ../../../bgp:lsp-options/bgp:unicast-rt-label-advertise = 'false'";
          default "per-instance";
          description
            "Configure a SID allocation mode of SRv6 for BGP.";
        }
        leaf advertise-sbfd-discriminator {
          type empty;
          description
            "Enable SRv6 SBFD reflector discriminator in BGP.";
        }
        leaf apply-sid-compress-type {
          type sid-compress-type;
          must ".='common' or /ni:network-instance/ni:instances/ni:instance[ni:name='_public_']/srv6:srv6/srv6:locators/srv6:locator[srv6:name=current()/../name]/srv6:compress-16";
          must "(.='common' and not(../apply-sid-flavor)) or .='compress'";
          must "not(../apply-sid-flavor) or (../apply-sid-flavor and /ni:network-instance/ni:instances/ni:instance[ni:name='_public_']/srv6:srv6/srv6:compress-16-mode and ((../apply-sid-flavor='coc-next' and /ni:network-instance/ni:instances/ni:instance[ni:name='_public_']/srv6:srv6/srv6:compress-16-mode='default') or ../apply-sid-flavor!='coc-next'))";
          default "common";
          description
            "Configure SID compress type.";
        }
        leaf-list apply-sid-flavor {
          when "../apply-sid-compress-type!='common'";
          type sid-flavor;
          max-elements 1;
          description
            "Configure SID flavor.";
        }
        leaf service-sid-type {
          type service-sid-type;
          must ".='unicast' or ((not(../auto-sid) or ../auto-sid = 'false') and not(../advertise-sbfd-discriminator) and (../apply-sid-compress-type='common'))";
          must "../../../../../../../../ni:name!='_public_' or .='unicast'";
          default "unicast";
          description
            "Configure the service SID type of SRv6 SID for BGP.";
        }
      }
    }
  }
  augment "/ni:network-instance/ni:instances/ni:instance/bgp:bgp/bgp:base-process/bgp:afs/bgp:af/bgp:ipv6-unicast" {
    description
      "BGP SRv6 configuration.";
    container locators {
      description
        "List of locators used by segment-routing IPv6 for BGP.";
      list locator {
        key "name";
        unique "service-sid-type";
        max-elements 2;
        description
          "Configure SRv6 locator.";
        leaf name {
          type leafref {
            path "/ni:network-instance/ni:instances/ni:instance/srv6:srv6/srv6:locators/srv6:locator/srv6:name";
          }
          description
            "Locator name.";
        }
        leaf apply-sid-mode {
          type apply-sid-mode;
          default "per-instance";
          description
            "Configure a SID allocation mode of SRv6 for BGP.";
        }
        leaf advertise-sbfd-discriminator {
          type empty;
          description
            "Enable SRv6 SBFD reflector discriminator in BGP.";
        }
        leaf apply-sid-compress-type {
          type sid-compress-type;
          must ".='common' or /ni:network-instance/ni:instances/ni:instance[ni:name='_public_']/srv6:srv6/srv6:locators/srv6:locator[srv6:name=current()/../name]/srv6:compress-16";
          must "(.='common' and not(../apply-sid-flavor)) or .='compress'";
          must "not(../apply-sid-flavor) or (../apply-sid-flavor and /ni:network-instance/ni:instances/ni:instance[ni:name='_public_']/srv6:srv6/srv6:compress-16-mode and ((../apply-sid-flavor='coc-next' and /ni:network-instance/ni:instances/ni:instance[ni:name='_public_']/srv6:srv6/srv6:compress-16-mode='default') or ../apply-sid-flavor!='coc-next'))";
          default "common";
          description
            "Configure SID compress type.";
        }
        leaf-list apply-sid-flavor {
          when "../apply-sid-compress-type!='common'";
          type sid-flavor;
          max-elements 1;
          description
            "Configure SID flavor.";
        }
        leaf service-sid-type {
          type service-sid-type;
          must ".='unicast' or (not(../advertise-sbfd-discriminator) and (../apply-sid-compress-type='common'))";
          must "../../../../../../../../ni:name!='_public_' or .='unicast'";
          default "unicast";
          description
            "Configure the service SID type of SRv6 SID for BGP.";
        }
      }
    }
    container locator-routes {
      when "../../../../../../ni:name='_public_'";
      description
        "List of locator routes.";
      list locator-route {
        key "locator-name";
        description
          "Configure a locator route in the BGP routing table.";
        leaf locator-name {
          type leafref {
            path "/ni:network-instance/ni:instances/ni:instance/srv6:srv6/srv6:locators/srv6:locator/srv6:name";
          }
          description
            "Referenced locator name.";
        }
        uses bgp:choice-policy-set {
          refine "policy-type" {
            description
              "Specify the route-policy or filter for route advertisement.";
          }
        }
      }
    }
  }
  augment "/ni:network-instance/ni:instances/ni:instance/srv6:srv6/srpolicy:srpolicy/srpolicy:policy-infos/srpolicy:policy-info" {
    description
      "Augment the SRv6 TE Policy model to add L3VPN tunnel information.";
    uses tunnel-info-ipv4;
    uses tunnel-info-ipv6;
  }
}
