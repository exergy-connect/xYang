module huawei-ietf-hardware-ext {
  yang-version 1.1;
  namespace "urn:huawei:yang:huawei-ietf-hardware-ext";
  prefix hw-ext;

  import ietf-hardware {
    prefix hw;
  }
  import huawei-extension {
    prefix ext;
  }

  organization
    "Huawei Technologies Co., Ltd.";
  contact
    "Huawei Industrial Base
     Bantian, Longgang
     Shenzhen 518129
     People's Republic of China
     Website: http://www.huawei.com
     Email: support@huawei.com
     ";
  description
    "The YANG module defines YANG objects which provide device management interfaces.";

  revision 2025-03-07 {
    description
      "Add leaf derive-component string length.";
    reference
      "Huawei private.";
  }
  revision 2018-03-31 {
    description
      "Initial revision.";
    reference
      "Huawei private.";
  }

  augment "/hw:hardware/hw:component" {
    description
      "Extended node for ietf-hardware.";
    leaf derive-component {
     
      type string {
        length "1..32";
      }
      config false;
      description
        "The derive from component name.
         The leaf only for netconf subtree filter.
         When netconf get/get config the leaf, return empty string.";
    }
  }
}
