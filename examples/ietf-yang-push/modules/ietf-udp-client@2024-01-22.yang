module ietf-udp-client {
  yang-version 1.1;
  namespace "urn:ietf:params:xml:ns:yang:ietf-udp-client";
  prefix udpc;

  import ietf-inet-types {
    prefix inet;
    reference
      "RFC 6991: Common YANG Data Types";
  }

  organization
    "IETF NETCONF (Network Configuration) Working Group";
  contact
    "WG Web:   <http:/tools.ietf.org/wg/netconf/>
     WG List:  <mailto:netconf@ietf.org>

     Authors:  Alex Huang Feng
               <mailto:alex.huang-feng@insa-lyon.fr>
               Pierre Francois
               <mailto:pierre.francois@insa-lyon.fr>";
  description
    "Defines a generic grouping for UDP-based client applications.

     Copyright (c) 2023 IETF Trust and the persons identified as
     authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC-to-be; see the RFC
     itself for full legal notices.";

  revision 2024-01-22 {
    description
      "Initial revision";
    reference
      "RFC-to-be: YANG Grouping for UDP Clients and UDP Servers";
  }

  grouping udp-client-grouping {
    description
      "Provides a reusable grouping for configuring a UDP client.";
    leaf remote-address {
      type inet:ip-address-no-zone;
      mandatory true;
      description
        "IP address of the UDP client, which can be an
         IPv4 address or an IPV6 address.";
    }
    leaf remote-port {
      type inet:port-number;
      mandatory true;
      description
        "Port number of the UDP client.";
    }
  }
}
