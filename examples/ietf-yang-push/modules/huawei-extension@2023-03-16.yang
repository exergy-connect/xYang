module huawei-extension {
  namespace "urn:huawei:yang:huawei-extension";
  prefix ext;

  organization
    "Huawei Technologies Co., Ltd.";
  contact
    "Huawei Industrial Base
     Bantian, Longgang
     Shenzhen 518129
     People's Republic of China
     Website: http://www.huawei.com
     Email: support@huawei.com";
  description
    "Huawei private extensions to the YANG language.";

  revision 2023-03-16 {
    description
      "Add advised-node.";
    reference
      "Huawei private.";
  }
  revision 2019-12-13 {
    description
      "Add refine-ext, deviation-ext and deviate-ext.";
    reference
      "Huawei private.";
  }
  revision 2019-11-09 {
    description
      "Update example for generated-by.";
    reference
      "Huawei private.";
  }
  revision 2019-09-26 {
    description
      "Add new extensions.";
    reference
      "Huawei private.";
  }
  revision 2019-05-07 {
    description
      "Init revision.";
    reference
      "Huawei private.";
  }

  extension support-filter {
    argument value;
    description
      "The syntax indicates whether a non-key node supports filtering in list or leaf-list node.
       The key node does not need to define this syntax because it must support filtering.
       The options are as follows: true, false. Default is false.";
  }
  extension value-replace {
    description
      "Value-replace.";
  }
  extension value-meaning {
    description
      "The syntax indicates meanings of some special values through using item and meaning syntax.";
  }
  extension item {
    argument value;
    description
      "The syntax indicates one special value and it is substatement of value-meaning. See value-meaning for usage.";
  }
  extension meaning {
    argument value;
    description
      "The syntax indicates meaning of the special value and it is substatement of item. See value-meaning for usage.";
  }
  extension case-sensitivity {
    argument value;
    description
      "The syntax indicates case sensitivity of string type or its derived type nodes.
       The options are as follows:
       1. lower-and-upper: Server can accept both lower and upper case, and it is case-sensitive when checking uniqueness.
       2. lower-or-upper: Server can accept both lower and upper case, and it is case-insensitive when checking uniqueness.
       3. lower-only: Server can accept lower case only.
       4. upper-only: Server can accept upper case only.
       5. lower2upper: Server transfers lower case into upper case automatically.
       6. upper2lower: Server transfers upper case into lower case automatically.
       Default is lower-and-upper.";
  }
  extension masklen {
    argument value;
    description
      "The syntax indicates total number of bit for the node using pub-type:bits8/bits16/bits32/bits64 type.";
  }
  extension bit {
    argument value;
    description
      "The syntax indicates the name of one bit for the node using pub-type:bits8/bits16/bits32/bits64 type.
       See masklen for usage.";
  }
  extension allowDelete {
    argument value;
    description
      "AllowDelete.";
  }
  extension value-range {
    argument value;
    description
      "The syntax indicates numerical range of value that can be entered using id-range type or its derived type nodes.";
  }
  extension task-name {
    argument value;
    description
      "The syntax indicates which task the module belongs to and should be defined before the root node.";
  }
  extension entry-from {
    argument value;
    description
      "Applies only to a list or presence container whose config is true.
       Entry-from specifies an instance to be automatically generated by the system
       based on other data or to be created by a user.";
  }
  extension node-ref {
    argument value;
    description
      "The syntax indicates the xpath of the data node for which the rpc operation is performed.
       If the rpc operation is performed for the entire system (the corresponding node cannot
       be found in the model tree), this syntax is not required.";
  }
  extension dynamic-default {
    description
      "The syntax indicates dynamic default value according to system or other nodes.";
  }
  extension default-value {
    argument value;
    description
      "The syntax indicates one dynamic default value and it is substatement of dynamic-default. See dynamic-default for usage.";
  }
  extension operation-exclude {
    argument value;
    description
      "The syntax indicates which operations are not supported.
       The options are as follows:
       create, delete, update and various combinations separated by '|'.";
  }
  extension filter {
    argument value;
    description
      "The syntax indicates rules satisfying specific constraints and it is substatement of operation-exclude or generated-by syntax.
       See operation-exclude or generated-by for usage.";
  }
  extension generated-by {
    argument value;
    description
      "The syntax indicates whether config datas are generated by the system.
       The options are as follows: system, user. Default is user.";
  }
  extension can-be-deleted {
    description
      "The syntax is used for the generated-by system scenario to indicate that the deleted configuration data cannot be automatically restored.";
  }
  extension upper2lower {
    argument value;
    description
      "Convert upper-case letters to lower-case letters.";
  }
  extension refine-ext {
    argument value;
    description
      "The syntax is used to define a private syntax for a xpath node in an extended manner, the value is xpath.";
  }
  extension deviation-ext {
    argument value;
    description
      "This syntax is used to tailor and customize multiple products for private syntax, the value is XPath.";
  }
  extension deviate-ext {
    argument value;
    description
      "This syntax is used to tailor and customize multiple products for private syntax, it is substatement of deviation-ext syntax,
       The options are as follows: add, delete, replace.
       See deviation-ext for usage.";
  }
  extension advised-node {
    argument value;
    description
      "This syntax is used to indicate the recommended xpath of the current node corresponding to the deprecated node.";
  }
}
