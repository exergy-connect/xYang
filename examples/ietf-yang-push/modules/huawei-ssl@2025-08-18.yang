module huawei-ssl {
  namespace "urn:huawei:yang:huawei-ssl";
  prefix ssl;

  import huawei-extension {
    prefix ext;
  }
  import huawei-pub-type {
    prefix pub-type;
  }
  import ietf-yang-types {
    prefix yang;
  }
  import huawei-pki {
    prefix pki;
  }

  organization
    "Huawei Technologies Co., Ltd.";
  contact
    "Huawei Industrial Base
     Bantian, Longgang
     Shenzhen 518129
     People's Republic of China
     Website: http://www.huawei.com
     Email: support@huawei.com";
  description
    "Secure Socket Layer (SSL).";

  revision 2025-08-18 {
    description
      "Added tlcp-policys.";
    reference
      "Huawei private.";
  }
  revision 2025-08-04 {
    description
      "Added pqc-x25519-mlkem for ecdh-group. Changed the must condition for the ecdh-group, and add sm2 enumeration to ssl-key-type.";
    reference
      "Huawei private.";
  }
  revision 2025-01-22 {
    description
      "Changed the maximum number of DTLS policies from 6 to 128.";
    reference
      "Huawei private.";
  }
  revision 2024-03-22 {
    description
      "Added sm4-gcm-sm3 and sm4-ccm-sm3 for ssl-cipher-type. Added curve-sm2 for ecdh-group. Added sm2-sm3 for signature-alg.";
    reference
      "Huawei private.";
  }
  revision 2023-12-11 {
    description
      "Changed the must condition for the pki-realm, trust-ca-load, cert-load, and crl-load nodes. Changed the maximum number of SSL/DTLS policies from 4 to 6, and modified pattern for cipher-suite-name leaf. Added the certificate-signature-algorithm-enable, forbidden-tls13-use-brainpoolr1, exclude-dhe-kex and ffdhe leaf nodes. Added the renegotiation leaf node. Added ecdhe-ecdsa-with-aes-128-gcm-sha256 and ecdhe-ecdsa-with-aes-256-gcm-sha384 for ssl-cipher-type.";
    reference
      "Huawei private.";
  }
  revision 2023-03-14 {
    description
      "Changed the type of the pki-realm and pki-domain-name nodes and the description of the pqc-kyber node, added the generated-by system attribute for the signature-algorithms node.";
    reference
      "Huawei private.";
  }
  revision 2022-08-24 {
    description
      "Initial revision.";
    reference
      "Huawei private.";
  }

 

  typedef ssl-password-type {
    type pub-type:password-extend;
    description
      "SSL password type.";
  }

  typedef ssl-cert-type {
    type enumeration {
      enum "asn1-cert" {
        value 1;
        description
          "Certype_asn1.";
      }
      enum "pem-cert" {
        value 2;
        description
          "Certype_pem.";
      }
      enum "pfx-cert" {
        value 3;
        description
          "Certype_pfx.";
      }
      enum "pem-chain" {
        value 4;
        description
          "Certype_pem-chain.";
      }
    }
    description
      "SSL certification type list.";
  }

  typedef ssl-key-type {
    type enumeration {
      enum "rsa" {
        value 1;
        description
          "Keytype_rsa.";
      }
      enum "dsa" {
        value 2;
        description
          "Keytype_dsa.";
      }
      enum "sm2" {
        value 3;
        description
          "Keytype_sm2.";
      }
    }
    description
      "SSL public key encryption type list.";
  }

  typedef ssl-crl-type {
    type enumeration {
      enum "asn1-crl" {
        value 1;
        description
          "Crltype_asn1.";
      }
      enum "pem-crl" {
        value 2;
        description
          "Crltype_pem.";
      }
    }
    description
      "Certification revocation type list.";
  }

  typedef ssl-ca-type {
    type enumeration {
      enum "asn1-ca" {
        value 1;
        description
          "Catype_asn1-ca.";
      }
      enum "pem-ca" {
        value 2;
        description
          "Catype_pem-ca.";
      }
      enum "pfx-ca" {
        value 3;
        description
          "Catype_pfx-ca.";
      }
    }
    description
      "Certificate authority type list.";
  }

  typedef ssl-version {
    type enumeration {
      enum "tls1.0" {
        value 2;
        status obsolete;
        description
          "SSL version tls1.0. This version is insecure and is not supported currently. It is used for query compatibility only.";
      }
      enum "tls1.1" {
        value 3;
        description
          "SSL version tls1.1.";
      }
      enum "tls1.2" {
        value 4;
        description
          "SSL version tls1.2.";
      }
      enum "tls1.3" {
        value 5;
        description
          "SSL version tls1.3.";
      }
    }
    description
      "SSL version type list.";
  }

  typedef encrypted {
    type enumeration {
      enum "ISENCRYPTED" {
        value 0;
        description
          "IS ENCRYPTED.";
      }
      enum "NOTENCRYPTED" {
        value 1;
        description
          "NOT ENCRYPTED.";
      }
    }
    description
      "SSL encrypted flag list.";
  }

  typedef ssl-bool {
    type enumeration {
      enum "enable" {
        value 1;
        description
          "Service Enable.";
      }
      enum "disable" {
        value 2;
        description
          "Service Disable.";
      }
    }
    description
      "Certificate Verify bool switch.";
  }

  typedef ssl-cipher-type {
    type enumeration {
      enum "rsa-with-aes-256-sha" {
        value 1;
        description
          "RSA-WITH-AES-256-SHA cipher suite.";
      }
      enum "rsa-with-aes-128-sha" {
        value 2;
        description
          "RSA-WITH-AES-128-SHA cipher suite.";
      }
      enum "dhe-rsa-with-aes-256-sha" {
        value 3;
        description
          "DHE-RSA-WITH-AES-256-SHA cipher suite.";
      }
      enum "dhe-dss-with-aes-256-sha" {
        value 4;
        description
          "DHE-DSS-WITH-AES-256-SHA cipher suite.";
      }
      enum "dhe-rsa-with-aes-128-sha" {
        value 5;
        description
          "DHE-RSA-WITH-AES-128-SHA cipher suite.";
      }
      enum "dhe-dss-with-aes-128-sha" {
        value 6;
        description
          "DHE-DSS-WITH-AES-128-SHA cipher suite.";
      }
      enum "rsa-aes-128-cbc-sha" {
        value 7;
        description
          "RSA-AES-128-CBC-SHA cipher suite.";
      }
      enum "rsa-aes-256-cbc-sha" {
        value 8;
        description
          "RSA-AES-256-CBC-SHA cipher suite.";
      }
      enum "rsa-aes-128-cbc-sha256" {
        value 9;
        description
          "RSA-AES-128-CBC-SHA256 cipher suite.";
      }
      enum "rsa-aes-256-cbc-sha256" {
        value 10;
        description
          "RSA-AES-256-CBC-SHA256 cipher suite.";
      }
      enum "dhe-dss-aes-128-cbc-sha" {
        value 11;
        description
          "DHE-DSS-AES-128-CBC-SHA cipher suite.";
      }
      enum "dhe-rsa-aes-128-cbc-sha" {
        value 12;
        description
          "DHE-RSA-AES-128-CBC-SHA cipher suite.";
      }
      enum "dhe-dss-aes-256-cbc-sha" {
        value 13;
        description
          "DHE-DSS-AES-256-CBC-SHA cipher suite.";
      }
      enum "dhe-rsa-aes-256-cbc-sha" {
        value 14;
        description
          "DHE-RSA-AES-256-CBC-SHA cipher suite.";
      }
      enum "dhe-dss-aes-128-cbc-sha256" {
        value 15;
        description
          "DHE-DSS-AES-128-CBC-SHA256 cipher suite.";
      }
      enum "dhe-rsa-aes-128-cbc-sha256" {
        value 16;
        description
          "DHE-RSA-AES-128-CBC-SHA256 cipher suite.";
      }
      enum "dhe-dss-aes-256-cbc-sha256" {
        value 17;
        description
          "DHE-DSS-AES-256-CBC-SHA256 cipher suite.";
      }
      enum "dhe-rsa-aes-256-cbc-sha256" {
        value 18;
        description
          "DHE-RSA-AES-256-CBC-SHA256 cipher suite.";
      }
      enum "rsa-with-aes-128-gcm-sha256" {
        value 19;
        description
          "RSA-WITH-AES-128-GCM-SHA256 cipher suite.";
      }
      enum "rsa-with-aes-256-gcm-sha384" {
        value 20;
        description
          "RSA-WITH-AES-256-GCM-SHA384 cipher suite.";
      }
      enum "dhe-rsa-with-aes-128-gcm-sha256" {
        value 21;
        description
          "DHE-RSA-WITH-AES-128-GCM-SHA256 cipher suite.";
      }
      enum "dhe-rsa-with-aes-256-gcm-sha384" {
        value 22;
        description
          "DHE-RSA-WITH-AES-256-GCM-SHA384 cipher suite.";
      }
      enum "dhe-dss-with-aes-128-gcm-sha256" {
        value 23;
        description
          "DHE-DSS-WITH-AES-128-GCM-SHA256 cipher suite.";
      }
      enum "dhe-dss-with-aes-256-gcm-sha384" {
        value 24;
        description
          "DHE-DSS-WITH-AES-256-GCM-SHA384 cipher suite.";
      }
      enum "ecdhe-rsa-with-aes-128-gcm-sha256" {
        value 25;
        description
          "ECDHE-RSA-WITH-AES-128-GCM-SHA256 cipher suite.";
      }
      enum "ecdhe-rsa-with-aes-256-gcm-sha384" {
        value 26;
        description
          "ECDHE-RSA-WITH-AES-256-GCM-SHA384 cipher suite.";
      }
      enum "aes-128-gcm-sha256" {
        value 27;
        description
          "AES-128-GCM-SHA256 cipher suite.";
      }
      enum "aes-256-gcm-sha384" {
        value 28;
        description
          "AES_256_GCM_SHA384 cipher suite.";
      }
      enum "chacha20-poly1305-sha256" {
        value 29;
        description
          "CHACHA20_POLY1305_SHA256 cipher suite.";
      }
      enum "aes-128-ccm-sha256" {
        value 30;
        description
          "AES_128_CCM_SHA256 cipher suite.";
      }
      enum "ecdhe-ecdsa-with-aes-128-gcm-sha256" {
        value 32;
        description
          "ECDHE_ECDSA_WITH_AES_128_GCM_SHA256 cipher suite.";
      }
      enum "ecdhe-ecdsa-with-aes-256-gcm-sha384" {
        value 33;
        description
          "ECDHE_ECDSA_WITH_AES_256_GCM_SHA384 cipher suite.";
      }
      enum "sm4-gcm-sm3" {
        value 34;
        description
          "TLS_SM4_GCM_SM3 cipher suite.";
      }
      enum "sm4-ccm-sm3" {
        value 35;
        description
          "TLS_SM4_CCM_SM3 cipher suite.";
      }
    }
    description
      "Enumeration of ssl cipher type.";
  }

  typedef ssl-cert-state {
    type enumeration {
      enum "valid" {
        value 1;
        description
          "The certificate is within the validity period.";
      }
      enum "about-to-expire" {
        value 2;
        description
          "The certificate is about to expire.";
      }
      enum "expired" {
        value 3;
        description
          "The certificate has expired.";
      }
    }
    description
      "Enumeration of ssl certificate validity state.";
  }

  typedef ssl-cert-file-type {
    type enumeration {
      enum "certificate" {
        value 1;
        description
          "Identity certificate.";
      }
      enum "crl" {
        value 2;
        description
          "List of revoked or suspended digital certificates.";
      }
      enum "trusted-ca" {
        value 3;
        description
          "Trusted CA certificate.";
      }
    }
    description
      "Enumeration of ssl certificate file type.";
  }

  typedef signature-type {
    type enumeration {
      enum "ecdsa-secp256r1-sha256" {
        value 1;
        description
          "Enable/disable ecdsa-secp256r1-sha256 signature algorithm.";
      }
      enum "ecdsa-secp384r1-sha384" {
        value 2;
        description
          "Enable/disable ecdsa-secp384r1-sha384 signature algorithm.";
      }
      enum "ecdsa-secp521r1-sha512" {
        value 3;
        description
          "Enable/disable ecdsa-secp521r1-sha512 signature algorithm.";
      }
      enum "ed25519" {
        value 4;
        description
          "Enable/disable ed25519 signature algorithm.";
      }
      enum "ed448" {
        value 5;
        description
          "Enable/disable ed448 signature algorithm.";
      }
      enum "rsa-pss-pss-sha256" {
        value 6;
        description
          "Enable/disable rsa-pss-pss-sha256 signature algorithm.";
      }
      enum "rsa-pss-pss-sha384" {
        value 7;
        description
          "Enable/disable rsa-pss-pss-sha384 signature algorithm.";
      }
      enum "rsa-pss-pss-sha512" {
        value 8;
        description
          "Enable/disable rsa-pss-pss-sha512 signature algorithm.";
      }
      enum "rsa-pss-rsae-sha256" {
        value 9;
        description
          "Enable/disable rsa-pss-rsae-sha256 signature algorithm.";
      }
      enum "rsa-pss-rsae-sha384" {
        value 10;
        description
          "Enable/disable rsa-pss-rsae-sha384 signature algorithm.";
      }
      enum "rsa-pss-rsae-sha512" {
        value 11;
        description
          "Enable/disable rsa-pss-rsae-sha512 signature algorithm.";
      }
      enum "rsa-pkcs1-sha256" {
        value 12;
        description
          "Enable/disable rsa-pkcs1-sha256 signature algorithm.";
      }
      enum "rsa-pkcs1-sha384" {
        value 13;
        description
          "Enable/disable rsa-pkcs1-sha384 signature algorithm.";
      }
      enum "rsa-pkcs1-sha512" {
        value 14;
        description
          "Enable/disable rsa-pkcs1-sha512 signature algorithm.";
      }
      enum "ecdsa-sha1" {
        value 15;
        description
          "Enable/disable ecdsa-sha1 signature algorithm.";
      }
      enum "ecdsa-sha224" {
        value 16;
        description
          "Enable/disable ecdsa-sha224 signature algorithm.";
      }
      enum "rsa-sha1" {
        value 17;
        description
          "Enable/disable rsa-sha1 signature algorithm.";
      }
      enum "rsa-sha224" {
        value 18;
        description
          "Enable/disable rsa-sha224 signature algorithm.";
      }
      enum "dsa-sha1" {
        value 19;
        description
          "Enable/disable dsa-sha1 signature algorithm.";
      }
      enum "dsa-sha224" {
        value 20;
        description
          "Enable/disable dsa-sha224 signature algorithm.";
      }
      enum "dsa-sha256" {
        value 21;
        description
          "Enable/disable dsa-sha256 signature algorithm.";
      }
      enum "dsa-sha384" {
        value 22;
        description
          "Enable/disable dsa-sha384 signature algorithm.";
      }
      enum "dsa-sha512" {
        value 23;
        description
          "Enable/disable dsa-sha512 signature algorithm.";
      }
    }
    description
      "Enumeration of ssl signature algorithm type.";
  }

  container ssl {
    description
      "Secure Socket Layer (SSL).";
    container ssl-policys {
      description
        "List of all SSL policys.";
      list ssl-policy {
        key "policy-name";
        max-elements 6;
        description
          "Configure SSL policy, which is a collection of certificate and certification agency's. Other features can use the SSL policy by referring to the SSL policy name.";
        leaf policy-name {
          type string {
            length "1..23";
            pattern "[a-z0-9_]*";
          }
          description
            "Name for identifying an SSL policy, the ranging from 1 to 23. You can only use underline, letter and digit. The letter does not differentiate the capital, and will transforms to the small letter.";
        }
        leaf pki-realm {
          type leafref {
            path "/pki:pki/pki:domains/pki:domain/pki:name";
          }
          must "not (../cert-loads/cert-load or ../crl-loads/crl-load or ../trust-ca-loads/trust-ca-load)";
          description
            "PKI domain.";
        }
        leaf mini-version {
          type ssl-version;
          default "tls1.2";
          description
            "Set SSL version, surport tls1.1 and tls1.2, the defult value is tls1.2.";
        }
        leaf cert-ver3-enable {
          type ssl-bool;
          default "disable";
          description
            "Whether to enable X509v3 verification for certificates.";
        }
        leaf crl-ver2-enable {
          type ssl-bool;
          default "disable";
          description
            "Whether to enable X509v2 verification for CRLs.";
        }
        leaf basic-const-enable {
          type ssl-bool;
          default "disable";
          description
            "Whether to enable Basic Constraints Field verification for certificates.";
        }
        leaf mini-path-len {
          type uint32 {
            range "1..1024";
          }
          default "1";
          description
            "Whether to enable minimum path length verification for certificates.";
        }
        leaf key-usage-enable {
          type ssl-bool;
          default "disable";
          description
            "Whether to enable Key Usage Field verification for certificates.";
        }
        leaf certificate-signature-algorithm-enable {
          type ssl-bool;
          default "disable";
          description
            "Whether to enable signature algorithm verification for certificates.";
        }
        leaf diffie-hellman-modulus {
          type uint32 {
            range "2048 | 3072 | 4096";
          }
          default "3072";
          description
            "Set modulus for diffie-hellman key exchange algorithm.";
        }
        leaf cipher-suite-name {
          type leafref {
            path "/ssl:ssl/ssl:ssl-cipher-suites/ssl:ssl-cipher-suite/ssl:cipher-suite-name";
          }
          description
            "Name for identifying a cipher suite name.";
        }
        leaf exclude-rsa-kex {
          type ssl-bool;
          default "enable";
          description
            "Whether to exclude RSA key exchange algorithm.";
        }
        leaf exclude-dhe-kex {
          type ssl-bool;
          default "disable";
          description
            "Whether to exclude DHE key exchange algorithm.";
        }
        leaf exclude-hmac-sha1 {
          type ssl-bool;
          default "enable";
          description
            "Whether to exclude SHA-1 HMAC algorithm.";
        }
        leaf exclude-ciphermode-cbc {
          type ssl-bool;
          default "enable";
          description
            "Whether to exclude Cipher Block Chaining (CBC) mode algorithm.";
        }
        leaf forbidden-tls13-use-brainpoolr1 {
          type ssl-bool;
          default "disable";
          description
            "Whether to ssl forbidden tls13 use brainpoolr1.";
        }
        leaf renegotiation {
          type ssl-bool;
          default "disable";
          description
            "Whether to enable SSL renegotiation.";
        }
        leaf-list feature-name {
          type string {
            length "1..50";
          }
          config false;
          description
            "Name statistics for features which have binded this SSL policy.";
        }
        container ecdh-group {
          must "not (./nist='false' and ./curve='false' and ./brainpool='false' and ./pqc-kyber='false' and ./ffdhe='false' and ./curve-sm2='false' and ./pqc-x25519-mlkem='false')";
          description
            "Configure the ecdh groups for SSL policy.";
          leaf nist {
            type boolean;
            default "false";
            description
              "Enable/disable nist groups of ecdh.";
          }
          leaf curve {
            type boolean;
            default "true";
            description
              "Enable/disable curve groups of ecdh.";
          }
          leaf brainpool {
            type boolean;
            default "true";
            description
              "Enable/disable brainpool groups of ecdh.";
          }
          leaf pqc-kyber {
            type boolean;
            default "false";
            description
              "Enable/disable X25519MLKEM768 and x25519-kyber512 for tls1.3. X25519MLKEM768 follows the draft-ietf-tls-hybrid-design, and x25519-kyber512 follows the draft-ietf-tls-hybrid-design-05 draft.";
          }
          leaf ffdhe {
            type boolean;
            default "false";
            description
              "Enable/disable ffdhe groups of ecdh.";
          }
          leaf curve-sm2 {
            type boolean;
            default "false";
            description
              "Enable/disable curveSM2 groups of ecdh.";
          }
          leaf pqc-x25519-mlkem {
            type boolean;
            default "false";
            description
              "Enable/disable X25519MLKEM768 for tls1.3. Note: Currently, the post-quantum cryptographic algorithm follows the draft-ietf-tls-hybrid-design.";
          }
        }
        container signature-alg {
          must "not (./ecdsa-secp256r1-sha256='false' and ./ecdsa-secp384r1-sha384='false' and ./ecdsa-secp521r1-sha512='false' and ./rsa-pss-pss-sha256='false' and ./rsa-pss-pss-sha384='false' and ./rsa-pss-pss-sha512='false' and ./rsa-pss-rsae-sha256='false' and ./rsa-pss-rsae-sha384='false' and ./rsa-pss-rsae-sha512='false' and ./rsa-pkcs1-sha256='false' and ./rsa-pkcs1-sha384='false' and ./rsa-pkcs1-sha512='false' and ./ecdsa-sha1='false' and ./ecdsa-sha224='false' and ./rsa-sha1='false' and ./rsa-sha224='false' and ./dsa-sha1='false' and ./dsa-sha224='false' and ./ed25519='false' and ./ed448='false' and ./dsa-sha256='false' and ./dsa-sha384='false' and ./dsa-sha512='false' and ./sm2-sm3='false')";
          description
            "Configure signature algorithms for SSL policy.";
          leaf ecdsa-secp256r1-sha256 {
            type boolean;
            default "false";
            description
              "Enable/disable ecdsa-secp256r1-sha256 signature algorithm.";
          }
          leaf ecdsa-secp384r1-sha384 {
            type boolean;
            default "false";
            description
              "Enable/disable ecdsa-secp384r1-sha384 signature algorithm.";
          }
          leaf ecdsa-secp521r1-sha512 {
            type boolean;
            default "false";
            description
              "Enable/disable ecdsa-secp521r1-sha512 signature algorithm.";
          }
          leaf ed25519 {
            type boolean;
            default "true";
            description
              "Enable/disable ed25519 signature algorithm.";
          }
          leaf ed448 {
            type boolean;
            default "true";
            description
              "Enable/disable ed448 signature algorithm.";
          }
          leaf rsa-pss-pss-sha256 {
            type boolean;
            default "true";
            description
              "Enable/disable rsa-pss-pss-sha256 signature algorithm.";
          }
          leaf rsa-pss-pss-sha384 {
            type boolean;
            default "true";
            description
              "Enable/disable rsa-pss-pss-sha384 signature algorithm.";
          }
          leaf rsa-pss-pss-sha512 {
            type boolean;
            default "true";
            description
              "Enable/disable rsa-pss-pss-sha512 signature algorithm.";
          }
          leaf rsa-pss-rsae-sha256 {
            type boolean;
            default "true";
            description
              "Enable/disable rsa-pss-rsae-sha256 signature algorithm.";
          }
          leaf rsa-pss-rsae-sha384 {
            type boolean;
            default "true";
            description
              "Enable/disable rsa-pss-rsae-sha384 signature algorithm.";
          }
          leaf rsa-pss-rsae-sha512 {
            type boolean;
            default "true";
            description
              "Enable/disable rsa-pss-rsae-sha512 signature algorithm.";
          }
          leaf rsa-pkcs1-sha256 {
            type boolean;
            default "false";
            description
              "Enable/disable rsa-pkcs1-sha256 signature algorithm.";
          }
          leaf rsa-pkcs1-sha384 {
            type boolean;
            default "false";
            description
              "Enable/disable rsa-pkcs1-sha384 signature algorithm.";
          }
          leaf rsa-pkcs1-sha512 {
            type boolean;
            default "false";
            description
              "Enable/disable rsa-pkcs1-sha512 signature algorithm.";
          }
          leaf ecdsa-sha1 {
            type boolean;
            default "false";
            description
              "Enable/disable ecdsa-sha1 signature algorithm.";
          }
          leaf ecdsa-sha224 {
            type boolean;
            default "false";
            description
              "Enable/disable ecdsa-sha224 signature algorithm.";
          }
          leaf rsa-sha1 {
            type boolean;
            default "false";
            description
              "Enable/disable rsa-sha1 signature algorithm.";
          }
          leaf rsa-sha224 {
            type boolean;
            default "false";
            description
              "Enable/disable rsa-sha224 signature algorithm.";
          }
          leaf dsa-sha1 {
            type boolean;
            default "false";
            description
              "Enable/disable dsa-sha1 signature algorithm.";
          }
          leaf dsa-sha224 {
            type boolean;
            default "false";
            description
              "Enable/disable dsa-sha224 signature algorithm.";
          }
          leaf dsa-sha256 {
            type boolean;
            default "false";
            description
              "Enable/disable dsa-sha256 signature algorithm.";
          }
          leaf dsa-sha384 {
            type boolean;
            default "false";
            description
              "Enable/disable dsa-sha384 signature algorithm.";
          }
          leaf dsa-sha512 {
            type boolean;
            default "false";
            description
              "Enable/disable dsa-sha512 signature algorithm.";
          }
          leaf sm2-sm3 {
            type boolean;
            default "false";
            description
              "Enable/disable sm2sig_sm3 signature algorithm.";
          }
        }
        container cert-loads {
          description
            "List of all SSL certificate file loaded by SSL policy.";
          list cert-load {
            must "not (../../pki-realm)";
            key "cert-file";
            description
              "Configure SSL certificate file loaded by SSL policy.";
            leaf cert-file {
              type string {
                length "1..64";
              }
              description
                "Cert file.";
            }
            leaf cert-type {
              type ssl-cert-type;
              must "(../cert-type='pfx-cert' and ((../is-mac and ../is-mac=1 and not (../key-file)) or (../key-file and not (../is-mac)))) or (../cert-type!='pfx-cert' and ../key-file and not (../is-mac))";
              mandatory true;
              description
                "CertType.";
            }
            leaf auth-code-crt {
              when "not(../cert-type='asn1-cert')";
              type ssl-password-type {
                length "1..168";
              }
              mandatory true;
              description
                "AuthCode.";
            }
            leaf is-mac {
              when "(../cert-type='pfx-cert')";
              type uint32 {
                range "0..1";
              }
              description
                "Mark for using MAC.";
            }
            leaf key-type {
              type ssl-key-type;
              mandatory true;
              description
                "KeyType.";
            }
            leaf auth-code-mac {
              when "(../cert-type='pfx-cert' and ../is-mac=1)";
              type ssl-password-type {
                length "1..168";
              }
              mandatory true;
              description
                "AuthCodeMac.";
            }
            leaf key-file {
              when "(../is-mac=0) or not(../is-mac)";
              type string {
                length "1..64";
              }
              description
                "KeyFile.";
            }
            leaf issuer-name {
              when "not(not(../cert-file)) or not(../cert-file)";
              type string {
                length "1..255";
              }
              config false;
              description
                "Issuer name.";
            }
            leaf valid-not-before {
              when "not(not(../cert-file)) or not(../cert-file)";
              type string {
                length "1..255";
              }
              config false;
              description
                "Validity Not Before.";
            }
            leaf valid-not-after {
              when "not(not(../cert-file)) or not(../cert-file)";
              type string {
                length "1..255";
              }
              config false;
              description
                "Validity Not After.";
            }
            leaf is-cert-file-encrypted {
              type encrypted;
              config false;
              description
                "Is cert-file Encrypted.";
            }
          }
        }
        container crl-loads {
          description
            "List of sslCrlLoad.";
          list crl-load {
            must "not (../../pki-realm)";
            key "crl-file";
            max-elements 2;
            description
              "Configure sslCrlLoad policy.";
            leaf crl-file {
              type string {
                length "1..64";
              }
              description
                "CrlFile.";
            }
            leaf crl-type {
              type ssl-crl-type;
              mandatory true;
              description
                "CrlType.";
            }
          }
        }
        container trust-ca-loads {
          description
            "List of sslTrustCALoads.";
          list trust-ca-load {
            must "not (../../pki-realm)";
            key "ca-file";
            max-elements 4;
            description
              "Configure sslTrustCALoad policy.";
            leaf ca-file {
              type string {
                length "1..64";
              }
              description
                "CaFile.";
            }
            leaf ca-type {
              type ssl-ca-type;
              mandatory true;
              description
                "CaType.";
            }
            leaf auth-code {
              when "(../ca-type='pfx-ca')";
              type ssl-password-type {
                length "1..168";
              }
              mandatory true;
              description
                "AuthCode.";
            }
          }
        }
        container certificate-files {
          config false;
          description
            "List of ssl certificate file.";
          list certificate-file {
            key "file-name file-type";
            description
              "Operational data of ssl certificate file.";
            leaf file-name {
              type string {
                length "1..64";
              }
              description
                "The file name of the certificate.";
            }
            leaf file-type {
              type ssl-cert-file-type;
              description
                "The file type of the certificate.";
            }
            container certificates {
              description
                "List of ssl certificate information.";
              list certificate {
                key "serial-number";
                description
                  "Operational data of ssl certificate.";
                leaf serial-number {
                  type string {
                    length "1..63";
                  }
                  description
                    "The serial number of the certificate.";
                }
                leaf version {
                  type string {
                    length "1..63";
                  }
                  description
                    "The version of the certificate.";
                }
                leaf issuer {
                  type string {
                    length "1..1023";
                  }
                  description
                    "The issuer of the certificate.";
                }
                leaf subject {
                  type string {
                    length "1..1023";
                  }
                  description
                    "The subject name of the certificate.";
                }
                leaf cert-state {
                  type ssl-cert-state;
                  description
                    "The state of the certificate.";
                }
                leaf start-time {
                  type yang:date-and-time;
                  description
                    "The validity start time of the certificate.";
                }
                leaf end-time {
                  type yang:date-and-time;
                  description
                    "The validity end time of the certificate.";
                }
                leaf signature-algorithm {
                  type string {
                    length "1..63";
                  }
                  description
                    "The signature algorithm of the certificate.";
                }
                leaf public-key-algorithm {
                  type string {
                    length "1..63";
                  }
                  description
                    "The public key algorithm of the certificate.";
                }
                leaf key-usage {
                  type string {
                    length "1..255";
                  }
                  description
                    "The key usage of the certificate.";
                }
                leaf subject-alternative-name {
                  type string {
                    length "1..255";
                  }
                  description
                    "The subject alternative name of the certificate.";
                }
                leaf common-name {
                  type string {
                    length "1..255";
                  }
                  description
                    "The common name of the certificate.";
                }
              }
            }
          }
        }
      }
    }
    container dtls-policys {
      description
        "List of all DTLS policys.";
      list dtls-policy {
        key "policy-name";
        max-elements 128;
        description
          "Configure DTLS policy, which is a collection of certificate and certification agency's. Other features can use the DTLS policy by referring to the DTLS policy name.";
        leaf policy-name {
          type string {
            length "1..23";
            pattern "[a-z0-9_]*";
          }
          description
            "Name for identifying an DTLS policy, the ranging from 1 to 23. You can only use underline, letter and digit. The letter does not differentiate the capital, and will transforms to the small letter.";
        }
        leaf pki-domain-name {
          type leafref {
            path "/pki:pki/pki:domains/pki:domain/pki:name";
          }
          description
            "PKI domain.";
        }
        leaf basic-const-enable {
          type ssl-bool;
          default "disable";
          description
            "Whether to enable Basic Constraints Field verification for certificates.";
        }
        leaf mini-path-len {
          type uint32 {
            range "1..1024";
          }
          default "1";
          description
            "Whether to enable minimum path length verification for certificates.";
        }
        leaf key-usage-enable {
          type ssl-bool;
          default "disable";
          description
            "Whether to enable Key Usage Field verification for certificates.";
        }
        leaf certificate-signature-algorithm-enable {
          type ssl-bool;
          default "disable";
          description
            "Whether to enable signature algorithm verification for certificates.";
        }
        leaf diffie-hellman-modulus {
          type uint32 {
            range "2048 | 3072 | 4096";
          }
          default "3072";
          description
            "Set modulus for diffie-hellman key exchange algorithm.";
        }
        leaf cipher-suite-name {
          type leafref {
            path "/ssl:ssl/ssl:ssl-cipher-suites/ssl:ssl-cipher-suite/ssl:cipher-suite-name";
          }
          description
            "Name for identifying a cipher suite name.";
        }
        leaf-list feature-name {
          type string {
            length "1..50";
          }
          config false;
          description
            "Name statistics for features which have binded this DTLS policy.";
        }
        leaf-list signature-algorithms {
         
          type signature-type;
          min-elements 1;
          description
            "Configure a signature algorithm list for the DTLS policy.";
        }
      }
    }
    container tlcp-policys {
      description
        "List of all TLCP policys.";
      list tlcp-policy {
        must "(encrypt-pki-domain-name and signature-pki-domain-name) or (not (encrypt-pki-domain-name) and not (signature-pki-domain-name))";
        key "policy-name";
        max-elements 6;
        description
          "Configure TLCP policy, which is a collection of certificate and certification agency's. Other features can use the TLCP policy by referring to the TLCP policy name.";
        leaf policy-name {
          type string {
            length "1..23";
            pattern "[a-z0-9_]*";
          }
          description
            "Name for identifying a TLCP policy, the ranging from 1 to 23. You can only use underline, letter and digit. The letter does not differentiate the capital, and will transforms to the small letter.";
        }
        leaf encrypt-pki-domain-name {
          type leafref {
            path "/pki:pki/pki:domains/pki:domain/pki:name";
          }
          description
            "Encryption-certificate PKI domain.";
        }
        leaf signature-pki-domain-name {
          type leafref {
            path "/pki:pki/pki:domains/pki:domain/pki:name";
          }
          description
            "Signature-certificate PKI domain.";
        }
        leaf basic-const-enable {
          type ssl-bool;
          default "disable";
          description
            "Whether to enable basic constraints field verification for certificates.";
        }
        leaf mini-path-len {
          type uint32 {
            range "1..1024";
          }
          default "1";
          description
            "Whether to enable minimum path length verification for certificates.";
        }
        leaf key-usage-enable {
          type ssl-bool;
          default "disable";
          description
            "Whether to enable key usage field verification for certificates.";
        }
        leaf cipher-suites {
          type bits {
            bit ecdhe-sm4-gcm-sm3 {
              position 0;
              description
                "ECDHE_SM4_GCM_SM3 cipher suite.";
            }
            bit ecdhe-sm4-cbc-sm3 {
              position 1;
              description
                "ECDHE_SM4_CBC_SM3 cipher suite.";
            }
            bit ecc-sm4-gcm-sm3 {
              position 2;
              description
                "ECC_SM4_GCM_SM3 cipher suite.";
            }
            bit ecc-sm4-cbc-sm3 {
              position 3;
              description
                "ECC_SM4_CBC_SM3 cipher suite.";
            }
            bit ecdhe-lac-sm4-gcm-sm3 {
              position 4;
              description
                "ECDHE_LAC_SM4_GCM_SM3 cipher suite.";
            }
          }
          must "current() != 0";
          default "ecdhe-sm4-gcm-sm3 ecdhe-sm4-cbc-sm3 ecc-sm4-gcm-sm3 ecc-sm4-cbc-sm3";
          description
            "List of TLCP cipher suites to configure.";
        }
      }
    }
    container ssl-cipher-suites {
      description
        "List of SSL cipher suites to configure.";
      list ssl-cipher-suite {
        key "cipher-suite-name";
        description
          "Configure SSL cipher suite.";
        leaf cipher-suite-name {
          type string {
            length "1..32";
            pattern "[^A-Z]*";
          }
          description
            "Configure name of cipher suite policy.";
        }
        leaf-list ssl-ciphers {
          type ssl-cipher-type;
          max-elements 4096;
          description
            "Configure list of SSL ciphers to configure policy.";
        }
      }
    }
    container certificate-alarm {
      description
        "Configure the certificate expiration alarm.";
      leaf early-warning-time {
        type uint32 {
          range "7..180";
        }
        units "d";
        default "90";
        description
          "Configure the time when an alarm is generated before the SSL certificate expires.";
      }
      leaf interval {
        type uint32 {
          range "1..168";
        }
        units "h";
        default "24";
        description
          "Configure the SSL certificate expiration check interval.";
      }
    }
  }
}
