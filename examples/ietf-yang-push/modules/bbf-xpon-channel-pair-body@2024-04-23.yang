submodule bbf-xpon-channel-pair-body {
  yang-version 1.1;
  belongs-to bbf-xpon {
    prefix bbf-xpon;
  }

  import bbf-xpon-types {
    prefix bbf-xpon-types;
  }
  import ietf-interfaces {
    prefix if;
  }
  import bbf-xpon-if-type {
    prefix bbf-xponift;
  }


  include "bbf-xpon-base";

  include "bbf-xpon-wavelength-profile-body";

  include "bbf-xpon-channel-partition-body";

  organization
    "Broadband Forum <https://www.broadband-forum.org>
     Fiber Access Networks Work Area";
  contact
    "Comments or questions about this Broadband Forum YANG module
     should be directed to <mailto:info@broadband-forum.org>.

     Editor:      Robert Peschi, Nokia

     PS Leader:   Joey Boyd, Adtran

     WA Director: Marta Seda, Calix";
  description
    "This submodule contains a collection of YANG definitions for
     managing channel pairs.

     Copyright (c) 2018-2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3; see
     the TR itself for full legal notices.";

  revision 2024-04-23 {
    description
      "Issue 3.
       * Approval Date:    2024-04-23.
       * Publication Date: 2024-04-23.";
    reference
      "TR-385i3: YANG Modules for PON Management
               <https://www.broadband-forum.org/technical/download/
                        TR-385_Issue-3.pdf>";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }
  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  grouping channel-pair-config-data {
    description
      "All configuration data for a channel pair.";
    leaf channel-group-ref {
      type if:interface-ref;
      must "derived-from-or-self(/if:interfaces/if:interface[if:name=current()]/if:type,'bbf-xponift:channel-group')" {
        error-message
          "Must reference a channel group.";
      }
      description
        "Reference to channel group. Note that it is not allowed
         to have several channel-pairs with identical downstream
         channel-ID or upstream channel-ID or transmit wavelength
         simultaneously active on the same chnanel-group.
         In particular there may be only a maximum of one 25GS-PON,
         one XGS-PON, one XG-PON and one G-PON active on the same
         channel group.
         The YANG model does not enforce these constraints which are
         assumed to be enforced or verified by the OLT network
         element software.";
    }
    leaf channel-partition-ref {
      type if:interface-ref;
      must "derived-from-or-self(/if:interfaces/if:interface[if:name=current()]/if:type,'bbf-xponift:channel-partition') and /if:interfaces/if:interface[if:name=current()]/channel-partition/channel-group-ref=../channel-group-ref" {
        error-message
          "Must reference a channel partition associated with the same channel group this pair is associated with.";
      }
      description
        "Reference to channel partition.";
    }
    leaf wavelength-prof-ref {
      when "derived-from-or-self(../channel-pair-type,'bbf-xpon-types:ngpon2-twdm') or derived-from-or-self(../channel-pair-type, 'bbf-xpon-types:ngpon2-ptp') or derived-from-or-self(../channel-pair-type,'bbf-xpon-types:xgs') or derived-from-or-self(../channel-pair-type,'bbf-xpon-types:twentyfivegs')";
      type wavelength-prof-ref;
      description
        "Reference to a wavelength profile. Applicable to XGS-PON,
         NG-PON2 and 25GS-PON only.";
      reference
        "ITU-T G.9807.1 Clause A.8.2 - Basic Wavelength and
         Optional Wavelength sets;
         MSA 25GS-PON Annex B";
    }
    leaf channel-pair-type {
      type identityref {
        base bbf-xpon-types:channel-pair-type-base;
      }
      mandatory true;
      description
        "Represents the type of channel pair
         (e.g., TDM 50G-PON, 25GS-PON, TWDM NG-PON2, PtP NG-PON2,
          XGS-PON, XG-PON, G-PON).";
    }
    leaf channel-pair-line-rate {
      when "derived-from-or-self(../channel-pair-type,'bbf-xpon-types:ngpon2-twdm') or derived-from-or-self(../channel-pair-type, 'bbf-xpon-types:ngpon2-ptp')" {
        description
          "Only applicable for Time Wavelength Division
           Multiplexing (TWDM) NG-PON2 or Point-to-Point (PtP)
           NG-PON2 channel pairs.";
      }
      type identityref {
        base bbf-xpon-types:channel-pair-line-rate-profile-base;
      }
      default "bbf-xpon-types:unplanned-cp-line-rate";
      description
        "Represents the planned downstream/upstream channel pair
         speed for NG-PON2. The line rates for
             XGS-PON (downstream 10Gbps/upstream 10Gbps),
             XG-PON(downstream 10Gbps/upstream 2.5Gbps) and
             G-PON (downstream 2.5Gbps/upstream 1.2Gbps)
         are fixed per ITU-T standards and need not be configured.";
    }
    leaf fiftyg-channel-pair-line-rate {
      when "derived-from-or-self(../channel-pair-type,'bbf-xpon-types:fiftyg-tdm') or derived-from-or-self(../channel-pair-type,'bbf-xpon-types:fiftyg-twdm')";
      type identityref {
        base bbf-xpon-types:fiftyg-channel-pair-line-rate-profile-base;
      }
      default "bbf-xpon-types:unplanned-50g-cp-line-rate";
      description
        "Represents the planned downstream/upstream channel pair
         speed for 50G-PON.";
      reference
        "ITU-T G.9804.3 Clause 9.2.1;
         ITU-T G.9804.2 Clause 1.1";
    }
    leaf twentyfivegs-channel-pair-line-rate {
      when "derived-from-or-self(../channel-pair-type,'bbf-xpon-types:twentyfivegs')";
      type identityref {
        base bbf-xpon-types:twentyfivegs-channel-pair-line-rate-profile-base;
      }
      default "bbf-xpon-types:unplanned-25gs-cp-line-rate";
      description
        "Represents the planned downstream/upstream channel pair
         speed for 25GS-PON.";
      reference
        "MSA 25GS-PON Table 6.1;
         MSA 25GS-PON Table 6.2";
    }
    leaf gpon-pon-id-interval {
      when "derived-from-or-self(../channel-pair-type, 'bbf-xpon-types:gpon')";
      type uint16 {
        range "0..60";
      }
      units "seconds";
      default "0";
      description
        "Specifies the frequency of transmission of the
         periodic downstream PON-ID PLOAM message for this G-PON.
         See ITU-T G.984.3 C.1. The default value '0' allows not
         to generate this PLOAM message, fulfilling ITU-T G.984.3
         C.2 requirement. This is only applicable to G-PON.";
      reference
        "ITU-T G.984.3 Clause C.1;
         ITU-T G.984.3 Clause C.2";
    }
  }

  grouping channel-pair-state-data {
    description
      "All state data for a channel pair.";
    leaf actual-downstream-wavelength {
      type uint32;
      units "0.01 nanometers";
      default "0";
      description
        "Represents the Actual Downstream wavelength of the
         channel pair. It is expressed in hundredths of nanometer
         to fit ITU-T precision requirements.";
    }
    leaf primary-ct-assigned {
      type boolean;
      default "false";
      description
        "If 'true', a channel termination with Primary type B
         role has been assigned to this channel pair.";
      reference
        "ITU-T G.989.3 Clause 18.2";
    }
    leaf secondary-ct-assigned {
      type boolean;
      default "false";
      description
        "If 'true', a channel termination with Secondary type B
         role has been assigned to this channel pair.";
      reference
        "ITU-T G.989.3 Clause 18.2";
    }
  }

  augment "/if:interfaces/if:interface/bbf-xpon:channel-pair" {
    description
      "Configuration of an xPON channel pair.";
    uses channel-pair-config-data;
  }
  augment "/if:interfaces-state/if:interface/bbf-xpon:channel-pair" {
    description
      "State data of an xPON channel pair.";
    uses channel-pair-state-data;
  }
}
