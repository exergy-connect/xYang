module huawei-bbf-qos-shaping-deviations-MA5800 {
  namespace "urn:huawei:yang:huawei-bbf-qos-shaping-deviations-MA5800";
  prefix bbf-qos-tm-devs-MA5800;

  import bbf-qos-shaping {
    prefix bbf-qos-shap;
  }
  import bbf-qos-traffic-mngt {
    prefix bbf-qos-tm;
  }
  import ietf-interfaces {
    prefix if;
  }

  organization
    "Huawei Technologies Co., Ltd.";
  contact
    "Huawei Industrial Base
     Bantian, Longgang
     Shenzhen 518129
     People's Republic of China
     Website: http://www.huawei.com
     Email: support@huawei.com";
  description
    "This module defines deviation statements for bbf-qos-shaping module.";

  revision 2024-04-08 {
    description
      "Initial revision.";
    reference
      "Huawei private.";
  }

  deviation "/bbf-qos-tm:tm-profiles/bbf-qos-shap:shaper-profile/bbf-qos-shap:name" {
    deviate replace {
      type string {
        length "1..32";
      }
    }
  }
  deviation "/bbf-qos-tm:tm-profiles/bbf-qos-shap:shaper-profile/bbf-qos-shap:shaper-type/bbf-qos-shap:single-token-bucket/bbf-qos-shap:single-token-bucket/bbf-qos-shap:pir" {
    deviate replace {
      type uint32 {
        range "64..102400000";
      }
    }
  }
  deviation "/bbf-qos-tm:tm-profiles/bbf-qos-shap:shaper-profile/bbf-qos-shap:shaper-type/bbf-qos-shap:single-token-bucket/bbf-qos-shap:single-token-bucket/bbf-qos-shap:pbs" {
    deviate replace {
      type uint32 {
        range "2000..1024000000";
      }
    }
  }
  deviation "/bbf-qos-tm:tm-profiles/bbf-qos-shap:shaper-profile/bbf-qos-shap:shaper-type/bbf-qos-shap:two-token-bucket/bbf-qos-shap:two-token-bucket/bbf-qos-shap:pir" {
    deviate replace {
      type uint32 {
        range "64..102400000";
      }
    }
  }
  deviation "/bbf-qos-tm:tm-profiles/bbf-qos-shap:shaper-profile/bbf-qos-shap:shaper-type/bbf-qos-shap:two-token-bucket/bbf-qos-shap:two-token-bucket/bbf-qos-shap:cir" {
    deviate replace {
      type uint32 {
        range "0..102400000";
      }
    }
  }
}
