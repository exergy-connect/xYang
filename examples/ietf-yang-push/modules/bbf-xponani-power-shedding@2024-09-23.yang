module bbf-xponani-power-shedding {
  yang-version 1.1;
  namespace "urn:bbf:yang:bbf-xponani-power-shedding";
  prefix bbf-xponani-pwr-shed;

  import ietf-interfaces {
    prefix if;
  }
  import bbf-xpon {
    prefix bbf-xpon;
  }
  import bbf-xponani {
    prefix bbf-xponani;
  }
  import bbf-xpon-if-type {
    prefix bbf-xponift;
  }
  import bbf-xponani-power-shedding-common {
    prefix bbf-xponani-pwr-shedc;
  }

  organization
    "Broadband Forum <https://www.broadband-forum.org>
     Common YANG Work Area.";
  contact
    "Comments or questions about this Broadband Forum YANG module
     should be directed to <mailto:help@broadband-forum.org>.

     Editor:      Robert Peschi, Nokia

     PS Leader:   Joey Boyd, Adtran

     WA Director: Marta Seda, Calix";
  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).

     Specifically, this module defines Optical Network Unit (ONU)
     power shedding at the Access Network Interface (ANI).

     Copyright (c) 2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-385; see
     the WT itself for full legal notices.";

  revision 2024-09-23 {
    description
      "TBD
       * Approval Date:    TBD.
       * Publication Date: TBD.";
    reference
      "TBD";
  }

  feature xpon-power-shedding {
    description
      "Indicates support for Optical Network Unit (ONU) power
       shedding.";
    reference
      "ITU-T G.988 Clause 9.1.7";
  }

  augment "/bbf-xpon:xpon" {
    if-feature "xpon-power-shedding";
    description
      "Power shedding profiles.";
    container power-shedding-profiles {
      description
        "Power shedding profiles.";
      uses bbf-xponani-pwr-shedc:power-shedding-profiles-list;
    }
  }
  augment "/if:interfaces/if:interface/bbf-xponani:ani" {
    if-feature "xpon-power-shedding";
    description
      "Associates an Optical Network Unit (ONU) power shedding
       profile to the ANI.";
    leaf power-shedding-profile-ref {
      type leafref {
        path "/bbf-xpon:xpon/bbf-xponani-pwr-shed:power-shedding-profiles/bbf-xponani-pwr-shed:power-shedding-profile/bbf-xponani-pwr-shed:name";
      }
      description
        "Optical Network Unit (ONU) power shedding profile
         reference.";
    }
  }
  augment "/if:interfaces-state/if:interface/bbf-xponani:ani" {
    if-feature "xpon-power-shedding";
    description
      "Optical Network Unit (ONU) power shedding class status
       information.";
    container power-shedding-class-status {
      when "../../if:type = 'bbf-xponift:ani'";
      config false;
      description
        "Optical Network Unit (ONU) power shedding class status
         information.";
      uses bbf-xponani-pwr-shedc:power-shedding-status-data;
    }
  }
}
