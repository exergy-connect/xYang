module huawei-xpon-board {
  yang-version 1;
  namespace "urn:huawei:yang:huawei-xpon-board";
  prefix hw-xpon-board;

  import huawei-board {
    prefix board;
  }

  organization
    "Huawei Technologies Co., Ltd.";
  contact
    "Huawei Industrial Base
     Bantian, Longgang
     Shenzhen 518129
     People's Republic of China
     Website: http://www.huawei.com
     Email: support@huawei.com
     ";
  description
    "This module contains xpon board data.";

  revision 2020-11-07 {
    description
      "Initial revision.";
    reference
      "ITU-T G.984, G.988, G.9807, G.987, G.989";
  }

  augment "/board:boards/board:board" {
    description
      "Augment board model with pon board specific configuration nodes.";
    container xpon {
      description
        "Configure the data node of pon board.";
      leaf ont-default-fec-switch {
        type enumeration {
          enum "enable" {
            value 1;
            description
              "Indicates that the ONT FEC switch is enabled.";
          }
          enum "use-profile-config" {
            value 2;
            description
              " Indicates that the ONT FEC switch is using line profile configuration.";
          }
        }
        description
          "Indicates the ONT default FEC switch.";
      }
    }
  }
}
