module bbf-l2-dhcpv4-relay-profile-common {
  yang-version 1.1;
  namespace "urn:bbf:yang:bbf-l2-dhcpv4-relay-profile-common";
  prefix bbf-l2-d4r-pc;

  import bbf-yang-types {
    prefix bbf-yang;
  }
  import bbf-subscriber-types {
    prefix bbf-subtype;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of common YANG definitions for
     supporting the Broadband Forum requirements on subscriber
     management via the DHCPv4 protocol as applicable to access
     network equipment. As such, this module is specific to access
     network equipment (e.g., BBF-specified Access Nodes and FTTdp
     DPUs).

     Specifically, this module contains the definition of a profile
     for subscriber information used by an L2 DHCPv4 Relay Agent in
     creating an Agent Circuit ID and Remote ID as described in
     TR-101i2.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }

  grouping l2-dhcpv4-relay-profiles {
    description
      "L2 DHCPv4 Relay Agent configuration profiles.";
    container l2-dhcpv4-relay-profiles {
      description
        "L2 DHCPv4 Relay Agent configuration profiles.";
      list l2-dhcpv4-relay-profile {
        key "name";
        description
          "An L2 DHCPv4 Relay Agent configuration profile.";
        leaf name {
          type bbf-yang:string-ascii64;
          description
            "Name of the profile.";
        }
        leaf max-packet-size {
          type uint16;
          units "bytes";
          default "1500";
          description
            "The maximum size of the DHCPv4 message to be created
             after appending the Agent Information option. Messages
             which, after appending the Relay Agent Information
             option, would exceed this configured maximum size shall
             be forwarded WITHOUT adding the Agent Information option.

             The 'max-packet-size' expresses the maximum size of the
             IP packet. The IP packet is the payload of the Ethernet
             frame and is inclusive of the IP header, the UDP header,
             and the DHCPv4 message.";
          reference
            "RFC 3046 Section 2.1";
        }
        container option82-format {
          description
            "Contains information that needs to be filled
             in option 82.";
          leaf-list suboptions {
            type enumeration {
              enum "circuit-id" {
                description
                  "Add the circuit ID sub-option (0x01) in option 82.

                   The value inserted is the value of the leaf
                   'circuit-id' defined in the instance in the list
                   'bbf-subprof:subscriber-profiles/bbf-subprof:
                   subscriber-profile' that is associated with the
                   interface, if any. If this leaf is unknown, then a
                   sub-option circuit ID will be generated according
                   to the syntax defined in the leaf
                   'default-circuit-id-syntax'.";
                reference
                  "RFC 3046 Section 3.1";
              }
              enum "remote-id" {
                description
                  "Add the remote ID sub-option (0x02) in option 82.

                   The value inserted is the value of the leaf
                   'remote-id' defined in the instance in the list
                   'bbf-subprof:subscriber-profiles/bbf-subprof:
                   subscriber-profile' that is associated with the
                   interface, if any. If this leaf is unknown, then a
                   sub-option remote ID will be generated according to
                   the syntax defined in the leaf
                   'default-remote-id-syntax'.";
                reference
                  "RFC 3046 Section 3.2";
              }
              enum "access-loop-characteristics" {
                description
                  "Signal the access loop characteristics in option
                   82. Access-loop-characteristics are added using the
                   vendor-specific sub-option with code 0x09.

                   The content of the sub-option is controlled via the
                   leaf 'access-loop-suboptions'.";
                reference
                  "RFC 4243 Section 3;
                   RFC 4243 Section 4";
              }
            }
            min-elements 1;
            description
              "Identifies the sub-options that should be part of
               option 82.";
          }
          leaf default-circuit-id-syntax {
            type bbf-yang:string-ascii63-or-empty;
            default "";
            description
              "To be used to generate a sub-option circuit ID when no
               'circuit-id' is provided for the VLAN sub-interface via
               a referenced 'bbf-subprof:subscriber-profiles/
               bbf-subprof:subscriber-profile'.

               The syntax is a string of ASCII characters that
               determines the actual value inserted in the sub-option.
               Parts of the syntax that are recognized as predefined
               keywords will be replaced by an actual value.";
            reference
              "TR-178 R-117";
          }
          leaf default-remote-id-syntax {
            type bbf-yang:string-ascii63-or-empty;
            default "";
            description
              "To be used to generate a sub-option remote ID when no
               'remote-id' is provided for the VLAN sub-interface via
               a referenced 'bbf-subprof:subscriber-profiles/
               bbf-subprof:subscriber-profile'.

               The syntax is a string of ASCII characters that
               determines the actual value inserted in the sub-option.
               Parts of the syntax that are recognized as predefined
               keywords will be replaced by an actual value.";
            reference
              "TR-178 R-120";
          }
          leaf access-loop-suboptions {
            type bbf-subtype:broadband-line-characteristics;
            description
              "Broadband line characteristics that are to be added in
               option 82.";
            reference
              "TR-178 R-121";
          }
          leaf start-numbering-from-zero {
            type boolean;
            default "false";
            description
              "In case the 'default-circuit-id-syntax' or
               'default-remote-id-syntax' indicates a Slot or a Port
               identification shall be added to the sub-option value,
               then this leaf determines if the slot/port numbering
               must start from 0 or 1.";
            reference
              "TR-178 R-118";
          }
          leaf use-leading-zeroes {
            type boolean;
            default "false";
            description
              "In case the 'default-circuit-id-syntax' or
               'default-remote-id-syntax' indicates a Slot or a Port
               identification shall be added to the sub-option value,
               then this leaf determines if the slot/port numbering
               must use leading 0's or not, i.e., generate a fixed-
               length string or a string with only meaningful digits.

               Note that the number of digits used to form the fixed-
               length string is device specific. A device may use the
               number of digits as specified in TR-101i2 Table 2/
               TR-156 Table 1 or a device may determine the number of
               digits by the maximum value for the Slot or a Port
               identification applicable to the device, i.e., if the
               maximum value is less than or equal to 9, one digit may
               be used; if the maximum value is less than or equal to
               99, two digits may be used, etc.";
            reference
              "TR-178 R-119;
               TR-101i2 Table 2;
               TR-156 Table 1";
          }
        }
      }
    }
  }
}
