module huawei-bbf-xpongemtcont-deviations-MA5800 {
  namespace "urn:huawei:yang:huawei-bbf-xpongemtcont-deviations-MA5800";
  prefix bbf-xpongemtcont-devs-MA5800;

  import bbf-xpongemtcont {
    prefix bbf-xpongemtcont;
  }

  organization
    "Huawei Technologies Co., Ltd.";
  contact
    "Huawei Industrial Base
     Bantian, Longgang
     Shenzhen 518129
     People's Republic of China
     Website: http://www.huawei.com
     Email: support@huawei.com";
  description
    "This module defines deviation statements for bbf-xpongemtcont module.";

  revision 2019-11-06 {
    description
      "Initial revision.";
    reference
      "Huawei private.";
  }

  deviation "/bbf-xpongemtcont:xpongemtcont/bbf-xpongemtcont:tconts/bbf-xpongemtcont:tcont/bbf-xpongemtcont:alloc-id" {
    deviate not-supported;
  }
  deviation "/bbf-xpongemtcont:xpongemtcont/bbf-xpongemtcont:gemports/bbf-xpongemtcont:gemport/bbf-xpongemtcont:gemport-id" {
    deviate not-supported;
  }
}
