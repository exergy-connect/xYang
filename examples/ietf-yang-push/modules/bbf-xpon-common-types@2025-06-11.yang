module bbf-xpon-common-types {
  yang-version 1.1;
  namespace "urn:bbf:yang:bbf-xpon-common-types";
  prefix xpon-common-types;

  import bbf-xpon-types {
    prefix bbf-xpon-types;
  }
  import bbf-xponani {
    prefix bbf-xponani;
  }
  import bbf-xpon-power-management {
    prefix bbf-xpon-pwr;
  }

  organization
    "Broadband Forum <https://www.broadband-forum.org>
     Common YANG Work Area.";
  contact
    "Comments or questions about this Broadband Forum YANG module
     should be directed to <mailto:help@broadband-forum.org>.

     Editor: XinWen Yao, Huawei";
  description
    "An experimental YANG module supporting xPON.";

  revision 2025-06-11 {
    description
      "Add new typedef";
    reference
      "Huawei private.";
  }
  revision 2024-04-01 {
    description
      "Initial revision.";
    reference
      "ITU-T G.984, G.988, G.9807, G.987, G.989";
  }

  identity xgt {
    base bbf-xpon-types:channel-pair-type-base;
    description
      "This identity is used to denote a xgt channel-pair.";
  }

  identity number-of-ethernet-ports {
    base bbf-xponani:ethernet-port-base-type;
    description
      "This identity is used to define the Ethernet LAN
       port number, no distinction between port speeds.";
    reference
      "ITU-T G.988 Clause 9.1.6 - Number of ports";
  }

  identity number-of-tdm-ports {
    base bbf-xponani:capability-base-type;
    description
      "This identity is used to define the ani tdm port type number.";
  }

  identity number-of-uplink-pon-ports {
    base bbf-xponani:capability-base-type;
    description
      "This identity is used to define the ani uplink pon port type number.";
  }

  identity power-state-normal {
    base bbf-xpon-pwr:power-state-base;
    description
      "Power management is normal by the Optical Network Unit(ONU).";
  }

  typedef general-onu-serial-number {
    type string {
      pattern "[ -~]{4}[0-9a-fA-F]{8}|[0-9a-fA-F]{16}";
    }
    description
      "A type meant for the serial number of an Optical Network
       Unit (ONU). In principle, ITU-T requires ONU vendors to
       have an ONU serial number start with four letters.
       However, to cope with real world deployments, it is also
       allowed that an ONU serial number starts with any four
       printable ASCII characters.In addition, serial numbers
       composed of 16 hexadecimal characters are also allowed.";
  }

  typedef gpon-pon-id-types {
    type string {
      pattern "[a-fA-F0-9]{14}|.{1,7}";
    }
    description
      "For G-PON, the PON Identifier (PON-ID) is entirely
       configurable with any binary value over 7 bytes,
       A string representing 7 hexadecimal octets expressed in
       ASCII or any string of 1 to 7 characters.";
  }

  typedef other-pon-id-types {
    type string {
      pattern "[a-fA-F0-9]{8}|.{1,4}";
    }
    description
      "For XG-PON, XGS-PON, 50G-PON, the PON Identifier (PON-ID)
       is entirely configurable and is 32 bits long.
       A string representing 4 hexadecimal octets expressed in
       ASCII or any string of 1 to 4 characters.";
  }

  typedef module-type {
    type enumeration {
      enum "gpon" {
        value 1;
        description
          "Transceiver module type:gpon.";
      }
      enum "epon" {
        value 2;
        description
          "Transceiver module type:epon.";
      }
      enum "10g-epon" {
        value 3;
        description
          "Transceiver module type:10g-epon.";
      }
      enum "xg-pon" {
        value 4;
        description
          "Transceiver module type:xg-pon.";
      }
      enum "xgs-pon" {
        value 9;
        description
          "Transceiver module type:xgs-pon.";
      }
      enum "gpon-and-xgpon" {
        value 10;
        description
          "Transceiver module type:gpon and xg-pon.";
      }
      enum "gpon-and-xgspon" {
        value 11;
        description
          "Transceiver module type:gpon and xgs-pon.";
      }
      enum "xgspon-and-50gspon" {
        value 12;
        description
          "Transceiver module type:xgs-pon and 50gs-pon.";
      }
      enum "50gs-pon" {
        value 13;
        description
          "Transceiver module type:50gs-pon.";
      }
      enum "50g-25g-pon" {
        value 14;
        description
          "Transceiver module type:50g-25g-pon.";
      }
      enum "50g-12dot5g-pon" {
        value 15;
        description
          "Transceiver module type:50g-12.5g-pon.";
      }
      enum "50g-xgs-g-pon" {
        value 16;
        description
          "Transceiver module type:50g-pon and xgs-pon and gpon.";
      }
      enum "gpon-and-xgtpon" {
        value 23;
        description
          "Transceiver module type:gpon and xgt-pon.";
      }
      enum "xgt-pon" {
        value 24;
        description
          "Transceiver module type:xgt-pon.";
      }
      enum "50gs-xgs-g-pon" {
        value 26;
        description
          "Transceiver module type:50gs-pon and xgs-pon and gpon.";
      }
      enum "xgt-or-xgs-combo-pon" {
        value 28;
        description
          "Transceiver module type:xgt-or-xgs-combo-pon.";
      }
    }
    description
      "Transceiver module type.";
  }

  typedef module-sub-type {
    type enumeration {
      enum "classbplus" {
        value 1;
        description
          "Transceiver module sub type:classbplus.";
      }
      enum "classcplus" {
        value 2;
        description
          "Transceiver module sub type:classcplus.";
      }
      enum "classb" {
        value 3;
        description
          "Transceiver module sub type:classb.";
      }
      enum "classcplusplus" {
        value 4;
        description
          "Transceiver module sub type:classcplusplus.";
      }
      enum "classd" {
        value 5;
        description
          "Transceiver module sub type:classd.";
      }
      enum "classbpluscplus" {
        value 7;
        description
          "Transceiver module sub type:class b+/class c+.";
      }
      enum "classb1" {
        value 8;
        description
          "Transceiver module sub type:class b1.";
      }
      enum "n2a" {
        value 33;
        description
          "Transceiver module sub type:n2a.";
      }
      enum "n2b" {
        value 34;
        description
          "Transceiver module sub type:n2b.";
      }
      enum "n1" {
        value 35;
        description
          "Transceiver module sub type:n1.";
      }
      enum "e1" {
        value 36;
        description
          "Transceiver module sub type:e1.";
      }
      enum "e2a" {
        value 37;
        description
          "Transceiver module sub type:e2a.";
      }
      enum "e2b" {
        value 38;
        description
          "Transceiver module sub type:e2b.";
      }
      enum "n1-n2a-e1-e2a" {
        value 39;
        description
          "Transceiver module sub type:n1/n2a/e1/e2a.";
      }
      enum "d1" {
        value 40;
        description
          "Transceiver module sub type:d1.";
      }
      enum "d2" {
        value 41;
        description
          "Transceiver module sub type:d2.";
      }
      enum "n2" {
        value 42;
        description
          "Transceiver module sub type:n2.";
      }
      enum "e2" {
        value 43;
        description
          "Transceiver module sub type:e2.";
      }
      enum "classdplus" {
        value 44;
        description
          "Transceiver module sub type:classdplus.";
      }
      enum "n2be2b" {
        value 49;
        description
          "Transceiver module sub type:n2b/e2b.";
      }
      enum "n1n2e1" {
        value 50;
        description
          "Transceiver module sub type:n1/n2/e1.";
      }
      enum "px20plus" {
        value 66;
        description
          "Transceiver module sub type:px20plus.";
      }
      enum "px20plusplus" {
        value 67;
        description
          "Transceiver module sub type:px20plusplus.";
      }
      enum "pr30" {
        value 97;
        description
          "Transceiver module sub type:pr30.";
      }
      enum "prx30" {
        value 99;
        description
          "Transceiver module sub type:prx30.";
      }
      enum "pr30plus" {
        value 103;
        description
          "Transceiver module sub type:pr30plus.";
      }
      enum "pr40" {
        value 101;
        description
          "Transceiver module sub type:pr40.";
      }
      enum "prx40" {
        value 102;
        description
          "Transceiver module sub type:prx40.";
      }
      enum "bpluspx20p" {
        value 129;
        description
          "Transceiver module sub type:bpluspx20p.";
      }
      enum "bpx20" {
        value 130;
        description
          "Transceiver module sub type:bpx20.";
      }
    }
    description
      "Transceiver module sub type.";
  }

  typedef used-type {
    type enumeration {
      enum "olt" {
        value 1;
        description
          "Transceiver used-type:olt.";
      }
      enum "ont" {
        value 2;
        description
          "Transceiver used-type:ont.";
      }
      enum "onu" {
        value 3;
        description
          "Transceiver used-type:onu.";
      }
      enum "onu-dq" {
        value 6;
        description
          "Transceiver used-type:onu with dq.";
      }
      enum "onu-eth" {
        value 7;
        description
          "Transceiver used-type:onu eth port.";
      }
    }
    description
      "Transceiver used-type.";
  }

  typedef module-grade {
    type enumeration {
      enum "commercial" {
        value 1;
        description
          "Transceiver module-grade:commercial.";
      }
      enum "industrial" {
        value 2;
        description
          "Transceiver module-grade:industrial.";
      }
      enum "enhanced-commercial" {
        value 3;
        description
          "Transceiver module-grade:enhanced commercial.";
      }
    }
    description
      "Transceiver module-grade.";
  }

  typedef port-channel-type {
    type enumeration {
      enum "gpon" {
        value 1;
        description
          "Indicates that the channel type of the PON port is GPON.";
      }
      enum "xgpon" {
        value 2;
        description
          "Indicates that the channel type of the PON port is XG-PON.";
      }
      enum "xgspon" {
        value 3;
        description
          "Indicates that the channel type of the PON port is XGS-PON.";
      }
      enum "50gspon" {
        value 4;
        description
          "Indicates that the channel type of the PON port is 50GS-PON.";
      }
      enum "xgtpon" {
        value 5;
        description
          "Indicates that the channel type of the PON port is XGT-PON.";
      }
    }
    description
      "Channel type of the PON port.";
  }

  typedef ont-nni-type {
    type enumeration {
      enum "rate2p5g1p25g" {
        value 1;
        description
          "Downstream rate 2.5Gbps, upstream rate 1.25Gbps.";
      }
      enum "rate10g2p5g" {
        value 2;
        description
          "Downstream rate 10Gbps, upstream rate 2.5Gbps.";
      }
      enum "rate10g10g" {
        value 3;
        description
          "Downstream rate 10Gbps, upstream rate 10Gbps.";
      }
      enum "rate50g12p5g" {
        value 6;
        description
          "Downstream rate 50Gbps, upstream rate 12.5Gbps.";
      }
      enum "rate50g25g" {
        value 7;
        description
          "Downstream rate 50Gbps, upstream rate 25Gbps.";
      }
      enum "rate50g50g" {
        value 8;
        description
          "Downstream rate 50Gbps, upstream rate 50Gbps.";
      }
      enum "rate12p5g12p5g" {
        value 9;
        description
          "Downstream rate 12.5Gbps, upstream rate 12.5Gbps.";
      }
    }
    description
      "Indicates the NNI type of the ONT.";
  }

  typedef access-scenario-type {
    type enumeration {
      enum "auto-negotiation" {
        value 0;
        description
          "Indicates that the ONT access scenario type is auto negotiation.";
      }
      enum "p2mp" {
        value 1;
        description
          "Indicates that the ONT access scenario type is p2mp.";
      }
      enum "common" {
        value 2;
        description
          "Indicates that the ONT access scenario type is common.";
      }
    }
    description
      "Type of access scenario.";
  }

  typedef onu-interoperability-mode {
    type enumeration {
      enum "itu-t" {
        value 1;
        description
          "The gpon onu interoperability mode is ituT.";
      }
      enum "ctc" {
        value 2;
        description
          "The gpon onu interoperability mode is ctc.";
      }
      enum "eric-v1" {
        value 3;
        description
          "The gpon onu interoperability mode is ericVa.";
      }
      enum "eric-v2" {
        value 4;
        description
          "The gpon onu interoperability mode is ericV2.";
      }
      enum "itu-tg984" {
        value 5;
        description
          "The gpon onu interoperability mode is ituTG984.";
      }
      enum "itu-tg988" {
        value 6;
        description
          "The gpon onu interoperability mode is ituTG988.";
      }
      enum "cuc" {
        value 7;
        description
          "The gpon onu interoperability mode is cuc.";
      }
      enum "cmcc" {
        value 8;
        description
          "The gpon onu interoperability mode is cmcc.";
      }
      enum "eci" {
        value 9;
        description
          "The gpon onu interoperability mode is eci.";
      }
      enum "mode1" {
        value 10;
        description
          "The gpon onu interoperability mode is mode1.";
      }
      enum "mode2" {
        value 11;
        description
          "The gpon onu interoperability mode is mode2.";
      }
      enum "mode2-v2" {
        value 12;
        description
          "The gpon onu interoperability mode is mode2V2.";
      }
      enum "mode3" {
        value 13;
        description
          "The gpon onu interoperability mode is mode3.";
      }
      enum "mode4" {
        value 14;
        description
          "The gpon onu interoperability mode is mode4.";
      }
      enum "mode2-v3" {
        value 15;
        description
          "The gpon onu interoperability mode is mode2V3.";
      }
      enum "mode2-v4" {
        value 16;
        description
          "The gpon onu interoperability mode is mode2V4.";
      }
      enum "mode5" {
        value 17;
        description
          "The gpon onu interoperability mode is mode5.";
      }
      enum "eci-v2" {
        value 18;
        description
          "The gpon onu interoperability mode is eciV2.";
      }
      enum "mode1-v2" {
        value 19;
        description
          "The gpon onu interoperability mode is mode1V2.";
      }
      enum "mode2-v5" {
        value 20;
        description
          "The gpon onu interoperability mode is mode2V5.";
      }
      enum "eric-v3" {
        value 21;
        description
          "The gpon onu interoperability mode is ericV3.";
      }
      enum "eric-v4" {
        value 22;
        description
          "The gpon onu interoperability mode is ericV4.";
      }
      enum "mode6" {
        value 23;
        description
          "The gpon onu interoperability mode is mode6.";
      }
      enum "eric-v5" {
        value 24;
        description
          "The gpon onu interoperability mode is ericV5.";
      }
      enum "mode7" {
        value 25;
        description
          "The gpon onu interoperability mode is mode7.";
      }
      enum "mode-1v3" {
        value 26;
        description
          "The gpon onu interoperability mode is mode1V3.";
      }
      enum "mode-1v4" {
        value 27;
        description
          "The gpon onu interoperability mode is mode1V4.";
      }
      enum "mode8" {
        value 28;
        description
          "The gpon onu interoperability mode is mode8.";
      }
    }
    description
      "The gpon onu interoperability mode.";
  }
}
