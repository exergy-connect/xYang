module bbf-dot1q-cfm-interfaces-state {
  yang-version 1.1;
  namespace "urn:bbf:yang:bbf-dot1q-cfm-interfaces-state";
  prefix bbf-cfm-if-s;

  import iana-if-type {
    prefix ianaift;
  }
  import ietf-yang-types {
    prefix yang;
  }
  import ietf-interfaces {
    prefix if;
  }
  import bbf-if-type {
    prefix bbfift;
  }
  import ieee802-dot1q-cfm-types {
    prefix cfm-types;
  }
  import bbf-dot1q-cfm {
    prefix bbf-cfm;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module is part of a collection of YANG definitions for
     supporting the Broadband Forum requirements on Connectivity Fault
     Management (CFM) Operations, Administration, and Maintenance
     (OAM) as applicable to access network equipment. As such, this
     module is specific to access network equipment (e.g., BBF-
     specified Access Nodes and FTTdp DPUs).

     Specifically, this module augments the IEEE 802.1Qcx CFM YANG
     data model to provide data nodes to report Maintenance Points
     present on an interface, i.e., the CFM stack of an interface.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }

  augment "/if:interfaces-state/if:interface" {
    when "derived-from-or-self(./if:type,'bbfift:vlan-sub-interface') or derived-from(./if:type,'bbfift:ethernet-like') or derived-from-or-self(./if:type,'ianaift:ptm') or derived-from-or-self(./if:type,'ianaift:ethernetCsmacd')" {
      description
        "CFM Maintenance Points are applicable only for VLAN
         sub-interfaces and for Ethernet-like interfaces which are
         interfaces with a type equal to or derived from one of the
         types 'bbfift:ethernet-like', 'ianaift:ptm' or
         'ianaift:ethernetCsmacd'.";
    }
    description
      "Augment the operational state of an interface with data nodes
       to report the CFM Maintenance Points existing on an
       interface.";
    container cfm-stack {
      presence "Indicates that CFM Maintenance Points exist on this
       interface.";
      description
        "This container provides information about the Maintenance
         Points on the interface.";
      list cfm-stack {
        key "md-level direction";
        description
          "An instance in the CFM stack of an interface is a
           Maintenance Point that exists on this interface. This
           instance contains data nodes that allow a user to locate
           the related CFM Maintenance Point configuration and
           operational data nodes.";
        leaf md-level {
          type cfm-types:md-level-type;
          description
            "The Maintenance Domain Level of the Maintenance Point.";
          reference
            "IEEE 802.1Q-2018 Clause 12.14.2.1.2b";
        }
        leaf direction {
          type cfm-types:mp-direction-type;
          description
            "The direction in which the Maintenance Point faces on the
             interface.";
          reference
            "IEEE 802.1Q-2018 Clause 12.14.2.1.2c";
        }
        leaf mac-address {
          type yang:mac-address;
          mandatory true;
          description
            "The MAC address of the Maintenance Point.";
          reference
            "IEEE 802.1Q-2018 Clause 12.14.2.1.3e";
        }
        choice maintenance-point {
          mandatory true;
          description
            "Indicates the type of Maintenance Point.";
          reference
            "IEEE 802.1Q-2018 Clause 12.14.2.1.3a";
          case mep {
            container mep {
              description
                "This container provides information about the
                 Maintenance Association Endpoint (MEP).";
              uses bbf-cfm:local-mep;
            }
          }
          case mhf {
            container mhf {
              description
                "This container provides information about the
                 Maintenance Domain Intermediate Point (MIP) Half
                 Function (MHF).";
              uses bbf-cfm:local-mhf;
            }
          }
        }
      }
    }
  }
}
