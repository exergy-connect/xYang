module meta-model {
  yang-version 1.1;
  namespace "urn:xtract:meta-model";
  prefix "mm";

  organization "Xtract";
  contact "Xtract";
  description "YANG schema for the Xtract meta-model. This schema validates data model definition files (YAML/JSON) that define entities, fields, and relationships.";

  revision "2026-01-15" {
    description "Initial version";
  }

  // Type definitions
  typedef date {
    type string {
      pattern '\d{4}-\d{2}-\d{2}';
    }
    description "Date in YYYY-MM-DD format";
  }

  typedef date-and-time {
    type string {
      pattern '\d{4}-\d{2}-\d{2}T\d{2}:\d{2}:\d{2}(\.\d+)?(Z|[+-]\d{2}:\d{2})?';
    }
    description "ISO 8601 date and time in format YYYY-MM-DDTHH:mm:ss[.sss][Z|±HH:mm]";
  }

  typedef entity-name {
    type string {
      length "1..64";
      pattern '[a-z_][a-z0-9_]*' {
        description
          "Entity names must start with a letter or underscore, followed by
           letters, digits, or underscores. They are normalized to lower case.";
      }
    }
    description "Entity name (letters, digits, underscores only, lowercase). The underscore count limit is configurable via max_name_underscores property (default: 2).";
  }

  typedef field-name {
    type string {
      length "1..64";
      pattern '[a-z_][a-z0-9_]*' {
        description
          "Field names must start with a letter or underscore, and are normalized to lower case.";
      }
    }
    description "Field name (letters, digits, underscores only, lowercase). The underscore count limit is configurable via max_name_underscores property (default: 2).";
  }

  typedef identifier {
    type string {
      pattern '^[a-zA-Z_][a-zA-Z0-9_]*$';
    }
    description "Valid Python identifier";
  }

  typedef version-string {
    type string {
      pattern '\d{2}\.\d{2}\.\d{2}\.\d+' {
        description "Version format: YY.MM.DD.N where YY is 2-digit year, MM is month, DD is day, and N is sequence number";
      }
    }
    description "Version string in format YY.MM.DD.N, auto-incremented during consolidation when changes are detected";
  }

  typedef primitive-type {
    type enumeration {
      enum string;
      enum integer;
      enum number;
      enum boolean;
      enum array;
      enum datetime;
      enum date;
      enum duration_in_days;
      enum qualified_string;
      enum qualified_integer;
      enum qualified_number;
    }
    description "Primitive field data type";
  }

  typedef rate-of-change {
    type enumeration {
      enum hourly;
      enum daily;
      enum weekly;
      enum monthly;
      enum quarterly;
      enum yearly;
      enum rarely;
      enum never;
    }
    description "Expected rate of change for an entity, indicating what is considered 'normal' change frequency";
  }

  typedef validation-mode {
    type enumeration {
      enum strict;
      enum warn;
      enum skip;
    }
    default strict;
    description "Data validation mode for entity";
  }


  typedef field-validation-mode {
    type enumeration {
      enum enforce;
      enum filter;
    }
    default enforce;
    description "Field validation mode. 'enforce' (default) - field constraints are enforced during validation, 'filter' - field value is filtered out (not included in data output)";
  }

  typedef qualified-source {
    type enumeration {
      enum ai;
      enum enum;
      enum schema;
      enum user;
      enum inferred;
      enum default;
      enum model;
    }
    description "Source of qualified value determination";
  }

  typedef change-history-policy {
    type union {
      type int32 {
        range "0..max";
      }
      type string {
        pattern '\*';
      }
    }
    description
      "Change history retention policy. Can be:
       - An integer N: Keep last N modification change IDs (default: 3)
       - '*': Keep infinite history
       - 0: Disabled (no modification history tracked)";
  }

  // Root container for data model
  container data-model {
    description "Root container for data model definition";
    leaf consolidated {
      type boolean;
      default false;
      description "Consolidated validation flag. Set to true for Phase 2 (combined cross-file validation) or false for Phase 1 (individual file validation). When true, file-scoped constraints (field limits, name limits) are skipped as they were already validated per-file. Used by MUST constraints to conditionally apply file-scoped validations.";
    }
    leaf name {
      type string;
      description "Name of the data model";
    }
    leaf version {
      type version-string;
      description "Version string";
    }
    leaf author {
      type string;
      description "Author of the data model";
    }
    leaf change_history {
      type change-history-policy;
      default 3;
      description
        "Default change history retention policy for all entities.
         Can be overridden per entity. Default: 3 (keep last 3 change ids)";
    }
    leaf include_x_fields {
      type boolean;
      default false;
      description "Include x-primaryKey and x-foreignKey extensions";
    }
    leaf allow_unlimited_fields {
      type boolean;
      default false;
      description "Allow entities to exceed the 7 non-array field limit";
    }
    leaf max_name_underscores {
      type uint8;
      default 2;
      description "Maximum number of underscores allowed in entity and field names. Default is 2 (allowing names like 'entity_field_name' with max 3 components). This constraint helps maintain readable names and encourages proper entity boundaries. Names exceeding this limit suggest missing entity boundaries and should be restructured into separate entities with relationships.";
    }
    leaf-list exclude {
      type string;
      description "List of strings to exclude data files from ingestion";
    }
    list entities {
      key name;
      min-elements 1;
      description "List of entity definitions";
      leaf name {
        type entity-name;
        mandatory true;
        description "Entity name";
        must "string-length(.) - string-length(translate(., '_', '')) <= number(../../../max_name_underscores)" {
          error-message "Entity name exceeds the maximum underscore limit configured in max_name_underscores (default: 2). Deep names suggest missing entity boundaries - create proper entities instead.";
          description "Validates that entity name has at most max_name_underscores underscores (default: 2) to constrain hierarchical depth and reduce parsing complexity.";
        }
      }
      leaf brief {
        type string;
        description "Brief one-line summary of the entity";
      }
      leaf description {
        type string;
        description "AI-friendly description of the entity type, not mandatory but STRONGLY recommended";
      }
      leaf-list primary_key {
        type field-name;
        min-elements 1;
        description "Ordered set of primary key fields for this entity";
        must "../fields[name = current()]" {
          description "Each primary_key value must reference an existing field in the entity's fields list";
        }
      }
      leaf-list required_fields {
        type field-name;
        description "List of required field names (auto-generated)";
      }
      must "/data-model/consolidated = true() or ../allow_unlimited_fields = 'true' or ../allow_unlimited_fields = true() or count(fields[type != 'array']) <= 7" {
        error-message "Entity has more than 7 non-array fields. Array fields are excluded from this count as they represent relationships to child entities. Consider splitting into multiple entities with foreign key relationships, or set allow_unlimited_fields: true to bypass this limit.";
        description "Validates that entity has at most 7 non-array fields, unless allow_unlimited_fields is true. Field limits are enforced in Phase 1 (individual file validation, consolidated=false) using the file's allow_unlimited_fields setting. In Phase 2 (combined validation, consolidated=true), this constraint is skipped as field limits are already validated per-file.";
      }
      list fields {
        key name;
        min-elements 1;
        description "List of field definitions for this entity. Best practice: limit to 7 non-array fields per entity to encourage proper abstraction. Array fields (type: 'array') are excluded from this count as they represent relationships to child entities, not direct attributes. This constraint can be bypassed with allow_unlimited_fields: true.";
        leaf name {
          type field-name;
          mandatory true;
          description "Field name";
          must "string-length(.) - string-length(translate(., '_', '')) <= number(../../../../../max_name_underscores)" {
            error-message "Field name exceeds the maximum underscore limit configured in max_name_underscores (default: 2). Deep names suggest missing entity boundaries - create proper entities instead.";
            description "Validates that field name has at most max_name_underscores underscores (default: 2) to constrain hierarchical depth and reduce parsing complexity.";
          }
        }
        leaf type {
      type primitive-type;
      mandatory true;
      description "Field data type";
    }
    leaf description {
      type string;
      description "AI-friendly field description";
    }
    leaf brief {
      type string;
      description "Brief one-line summary of the field";
    }
    leaf primaryKey {
      type boolean;
      default false;
      description "Marks this field as part of the primary key";
    }
    container foreignKey {
      presence "Foreign key is defined";
      description "Foreign key relationship. YANG constraints validate: (1) referenced entity exists, (2) foreign key field references parent's primary key.";
      leaf entity {
        type leafref {
          path "/data-model/entities/name";
          require-instance true;
        }
        mandatory true;
        description "Name of the referenced entity. Must reference an entity that exists in the data model.";
      }
      leaf field {
        type leafref {
          path "/data-model/entities/fields/name";
          require-instance true;
        }
        mandatory true;
        description "Name of the field in the referenced entity. Must reference a field that exists in the entity specified by entity.";
        must "/data-model/consolidated = false() or deref(../entity)/../fields[name = current()]" {
          error-message "Foreign key field must exist in the referenced entity's fields";
          description "Validates that the field exists in the entity specified by foreignKey.entity. Only enforced during consolidated validation (Phase 2) when cross-file references can be resolved.";
        }
        must "/data-model/consolidated = false() or deref(../entity)/../primary_key[. = current()]" {
          error-message "Foreign key field must reference one of the parent entity's primary key fields";
          description "Validates that the foreignKey.field references one of the parent entity's primary_key fields. Only enforced during consolidated validation (Phase 2) when cross-file references can be resolved.";
        }
      }
    }
    leaf min {
      type int32;
      description "Minimum length for string fields, or minimum value for numeric fields";
    }
    leaf max {
      type int32;
      description "Maximum length for string fields, or maximum value for numeric fields";
    }
    leaf minDate {
      type date;
      description "Minimum date value for date or datetime fields (YYYY-MM-DD format). Values must be on or after this date. Only applicable to fields with type 'date' or 'datetime'.";
      must "../type = 'date' or ../type = 'datetime'" {
        error-message "minDate can only be used with fields of type 'date' or 'datetime'";
        description "Validates that minDate is only specified for date or datetime fields";
      }
      must "not(../maxDate) or number(.) <= number(../maxDate)" {
        error-message "minDate must be less than or equal to maxDate when both are specified";
        description "Validates that minDate is not greater than maxDate when both date constraints are present";
      }
    }
    leaf maxDate {
      type date;
      description "Maximum date value for date or datetime fields (YYYY-MM-DD format). Values must be on or before this date. Only applicable to fields with type 'date' or 'datetime'.";
      must "../type = 'date' or ../type = 'datetime'" {
        error-message "maxDate can only be used with fields of type 'date' or 'datetime'";
        description "Validates that maxDate is only specified for date or datetime fields";
      }
      must "not(../minDate) or number(.) >= number(../minDate)" {
        error-message "maxDate must be greater than or equal to minDate when both are specified";
        description "Validates that maxDate is not less than minDate when both date constraints are present";
      }
    }
    leaf-list enum {
      type union {
        // Tried in declaration order
        type int32;
        type decimal64 {
          fraction-digits 2;
        }
        type string;
      }
      description "List of allowed enum values";
    }
    leaf default {
      type union {
        type string;
        type int32;
        type decimal64 {
          fraction-digits 2;
        }
        type boolean;
      }
      description "Default value for this field";
    }
    leaf required {
      type boolean;
      default false;
      description "Whether this field is required. Primary key fields are automatically required in the normalized JSON model, but users can mark other fields as required too.";
      must "not(../default) or . = false()" {
        error-message "A required field cannot have a default value. If required is true, default must not be specified.";
        description "A required field cannot have a default value. If required is true, default must not be specified.";
      }
    }
    container item_type {
      when "../type = 'array'";
      description "Required for array fields - specifies the type of each item";
      leaf primitive {
        type primitive-type;
        description "Primitive type (string, integer, etc.)";
      }
      leaf entity {
        type entity-name;
        description "Entity reference type";
      }
      container foreignKey {
        presence "Foreign key type";
        description "Foreign key reference type";
        leaf entity {
          type leafref {
            path "/data-model/entities/name";
            require-instance true;
          }
          mandatory true;
          description "Name of the referenced entity. Must reference an entity that exists in the data model.";
        }
        leaf field {
          type leafref {
            path "/data-model/entities/fields/name";
            require-instance true;
          }
          mandatory true;
          description "Name of the field in the referenced entity. Must reference a field that exists in the entity specified by entity.";
          must "/data-model/consolidated = false() or deref(../entity)/../fields[name = current()]" {
            error-message "Foreign key field must exist in the referenced entity's fields";
            description "Validates that the field exists in the entity specified by foreignKey.entity. Only enforced during consolidated validation (Phase 2) when cross-file references can be resolved.";
          }
          must "/data-model/consolidated = false() or deref(../entity)/../primary_key[. = current()]" {
            error-message "Foreign key field must reference one of the parent entity's primary key fields";
            description "Validates that the foreignKey.field references one of the parent entity's primary_key fields. Only enforced during consolidated validation (Phase 2) when cross-file references can be resolved.";
          }
        }
      }
      container primitive-object {
        presence "Primitive object type";
        leaf primitive {
          type primitive-type;
          mandatory true;
          description "Primitive type in object form";
        }
      }
    }
    leaf-list aliases {
      type field-name;
      description "Alternative names for this field";
    }
    leaf validation {
      type field-validation-mode;
      default enforce;
      description "Field validation mode. 'enforce' (default) - field constraints (min, max, minDate, maxDate, enum) are enforced during validation, 'filter' - the field value is filtered out (not included in the data output). Use 'filter' to exclude field values from consolidated data while keeping the field definition in the schema.";
    }
    container computed {
      presence "Computed field is defined";
      description "Computed field definition. When present, this field's value is calculated from other fields using the specified operation. Computed fields are marked as readOnly in JSON Schema and are excluded from required_fields.";
      leaf operation {
        type enumeration {
          enum add {
            description "Add operation: fields[0] + fields[1]. Valid for integer/number. Returns same type as operands. Requires exactly 2 fields.";
          }
          enum subtraction {
            description "Subtraction operation: fields[0] - fields[1]. Valid for date/datetime (returns duration_in_days) and integer/number (returns same type). Requires exactly 2 fields.";
          }
          enum multiplication {
            description "Multiplication operation: fields[0] * fields[1]. Valid for integer/number. Returns same type as operands. Requires exactly 2 fields.";
          }
          enum division {
            description "Division operation: fields[0] / fields[1]. Valid for integer/number. Returns same type as operands. Requires exactly 2 fields.";
          }
          enum min {
            description "Minimum operation: minimum of all fields. Valid for date, datetime, integer, number. Returns same type as input fields. Requires 2 or more fields.";
          }
          enum max {
            description "Maximum operation: maximum of all fields. Valid for date, datetime, integer, number. Returns same type as input fields. Requires 2 or more fields.";
          }
        }
        mandatory true;
        description "Operation to perform on the referenced fields";
      }
      list fields {
        key field;
        min-elements 2;
        max-elements 100;
        description "List of field references for the computed operation. For binary operations (add, subtraction), exactly 2 fields required. For aggregations (min, max), 2 or more fields required (up to 100 fields).";
        leaf field {
          type field-name;
          mandatory true;
          description "Field name to reference.";
          must "/data-model/consolidated = false() or ((not(../entity) and count(../../../../../fields[name = current()]) = 1) or (../entity and count(deref(../entity)/../fields[name = current()]) = 1))" {
            error-message "Computed field reference must exist in the specified entity (or current entity if not specified)";
            description "Validates that the field exists: in current entity when entity is omitted, or in referenced entity when entity is specified. Only enforced during consolidated validation (Phase 2) when cross-file references can be resolved.";
          }
        }
        leaf entity {
          type leafref {
            path "/data-model/entities/name";
            require-instance true;
          }
          description "Entity name for cross-entity field reference (optional).";
          must "/data-model/consolidated = false() or count(../../../../../fields[foreignKey/entity = current()]) = 1" {
            error-message "Cross-entity computed field references require a foreign key field in the current entity that references the target entity";
            description "When entity is specified, there must be at least one field in the current entity with a foreignKey referencing this entity. Only enforced during consolidated validation (Phase 2) when cross-file references can be resolved.";
          }
        }
      }
      must "(operation != 'add' and operation != 'subtraction') or count(fields) = 2" {
        error-message "Binary operations (add, subtraction) require exactly 2 fields";
        description "Validates that binary operations have exactly 2 field references";
      }
      must "(operation != 'min' and operation != 'max') or count(fields) >= 2" {
        error-message "Aggregation operations (min, max) require at least 2 fields";
        description "Validates that aggregation operations have at least 2 field references";
      }
    }
    }
    list parents {
        key child_fk;
        max-elements 3;
        description "List of parent relationships for hierarchical normalization. YANG constraints validate: (1) child_fk field exists and has foreignKey, (2) parent entity exists and has primary key, (3) foreign key references parent's primary key, (4) cross-entity field name matches parent PK, (5) field types match.";
        leaf child_fk {
        type leafref {
          path "../../fields/name";
          require-instance true;
        }
        mandatory true;
        description "Child foreign key field name. Must reference a field in the current entity's fields list that has a foreignKey definition.";
        must "deref(current())/../foreignKey" {
          error-message "Child foreign key field must have a foreignKey definition";
          description "Validates that child_fk field has a foreignKey definition.";
        }
        must "/data-model/consolidated = false() or /data-model/entities[name = deref(current())/../foreignKey/entity]" {
          error-message "Foreign key entity must exist in the data model";
          description "Validates that the entity referenced in the child_fk field's foreignKey exists in the data model. Only enforced during consolidated validation (Phase 2) when cross-file references can be resolved.";
        }
        must "/data-model/consolidated = false() or /data-model/entities[name = deref(current())/../foreignKey/entity]/fields[name = deref(current())/../foreignKey/field]" {
          error-message "Foreign key field must exist in the referenced entity's fields";
          description "Validates that the field referenced in foreignKey.field exists in the entity specified by foreignKey.entity. Only enforced during consolidated validation (Phase 2) when cross-file references can be resolved.";
        }
        must "/data-model/consolidated = false() or /data-model/entities[name = deref(current())/../foreignKey/entity]/primary_key" {
          error-message "Parent entity must have a primary key defined";
          description "Validates that the parent entity has a primary_key field defined. Only enforced during consolidated validation (Phase 2) when cross-file references can be resolved.";
        }
        must "/data-model/consolidated = false() or /data-model/entities[name = deref(current())/../foreignKey/entity]/primary_key[. = deref(current())/../foreignKey/field]" {
          error-message "Foreign key field must reference one of the parent entity's primary key fields";
          description "Validates that the foreignKey.field references one of the parent entity's primary_key fields. Only enforced during consolidated validation (Phase 2) when cross-file references can be resolved.";
        }
        must "/data-model/consolidated = false() or deref(current())/../type = " +
             "deref(deref(current())/../foreignKey/entity)/../fields[name = deref(current())/../foreignKey/field]/type" {
          error-message "Child foreign key field type must match parent primary key field type";
          description "Validates that the child foreign key field's type matches the parent primary key field's type. Only enforced during consolidated validation (Phase 2) when cross-file references can be resolved.";
        }
      }
      leaf parent_array {
        type leafref {
          path "/data-model/entities/fields/name";
          require-instance true;
        }
        mandatory true;
        description "Parent's array field name where children are nested. References a field name that must exist in some entity's fields list and be of type 'array'.";
        must "/data-model/consolidated = false() or /data-model/entities[name = deref(../child_fk)/../foreignKey/entity]/fields[name = current()]" {
          error-message "Parent array field must exist in the parent entity's fields (specified by child_fk's foreignKey)";
          description "Validates that parent_array references a field in the specific parent entity (looked up via child_fk's foreignKey). Only enforced during consolidated validation (Phase 2) when cross-file references can be resolved.";
        }
        must "/data-model/consolidated = false() or deref(deref(../child_fk)/../foreignKey/entity)/../fields[name = current()]/type = 'array'" {
          error-message "Parent array field must be of type 'array'";
          description "Validates that the field referenced by parent_array is of type 'array'. Only enforced during consolidated validation (Phase 2) when cross-file references can be resolved.";
        }
      }
    }
    leaf change_history {
      type change-history-policy;
      description "Change history retention policy for this entity. Overrides model-level default.";
    }
    leaf v {
      type version-string;
      description "Model version of this entity, added during consolidation. NOTE: This field is automatically added during consolidation and should NOT be included in source YAML files.";
    }
    leaf c {
      type int32;
      description "Change ID when this entity was created. NOTE: This field is automatically added during consolidation and should NOT be included in source YAML files.";
      must "/data-model/consolidated = false() or /data-model/changes[id = current()]" {
        error-message "c must reference a valid change ID in the changes list";
        description "c must reference a valid change ID in the changes list. Only enforced during consolidated validation (Phase 2) when change IDs are available.";
      }
    }
    leaf-list m {
      type int32;
      description
        "List of change IDs when this entity was modified (history).
         The size of this list is controlled by the change_history policy.
         NOTE: This field is automatically added during consolidation and should NOT be included in source YAML files.";
      must "/data-model/consolidated = false() or /data-model/changes[id = current()]" {
        error-message "Each m value must reference a valid change ID in the changes list";
        description "Each m value must reference a valid change ID in the changes list. Only enforced during consolidated validation (Phase 2) when change IDs are available.";
      }
    }
    leaf rate_of_change {
      type rate-of-change;
      description "Expected rate of change for this entity type, indicating what is considered 'normal' change frequency (e.g., hourly, daily, quarterly)";
    }
    leaf-list tools {
      type string;
      description "Optional list of tools that can provide additional details about this entity, such as real-time streaming telemetry or historical data";
    }
    leaf validation {
      type validation-mode;
      default strict;
      description "Data validation mode for this entity";
    }
    }
    list changes {
      key id;
      description "Change tracking records. NOTE: This list is automatically generated during consolidation and should NOT be included in source YAML files.";
      leaf id {
        type int32;
        mandatory true;
        description "Unique change identifier, monotonically increasing";
      }
      leaf timestamp {
        type date-and-time;
        mandatory true;
        description "ISO 8601 timestamp of the change";
      }
      leaf author {
        type string;
        description "Author of the change";
      }
      leaf note {
        type string;
        description "Optional note describing the change";
      }
      leaf git_commit_hash {
        type string;
        description "Git commit hash corresponding to this change";
      }
    }
  }
}
