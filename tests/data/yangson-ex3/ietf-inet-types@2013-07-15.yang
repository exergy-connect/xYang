module ietf-inet-types {
  yang-version 1.1;
  namespace "urn:ietf:params:xml:ns:yang:ietf-inet-types";
  prefix inet;

  revision 2013-07-15;

  typedef port-number {
    type uint16 {
      range "0..65535";
    }
  }

  typedef ipv4-address-no-zone {
    type string;
  }
}
