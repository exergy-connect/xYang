module ietf-inet-types {
  yang-version 1.1;
  namespace "urn:ietf:params:xml:ns:yang:ietf-inet-types";
  prefix inet;

  revision 2010-09-24;

  typedef port-number {
    type uint16 {
      range "0..65535";
    }
  }
}
