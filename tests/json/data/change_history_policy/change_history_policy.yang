module change-history-policy-test {
  yang-version 1.1;
  namespace "urn:test:change-history";
  prefix "ch";

  typedef change-history-policy {
    type union {
      type uint32;
      type string {
        pattern '\*';
      }
    }
    description
      "Change history retention policy. Can be:
       - An integer N: Keep last N modification change IDs (default: 3)
       - '*': Keep infinite history
       - 0: Disabled (no modification history tracked)";
  }

  container data-model {
    description "Root container";
    leaf change_history_policy {
      type change-history-policy;
      default 3;
      description "Change history retention policy";
    }
  }
}
