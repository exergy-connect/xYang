module m {
  yang-version 1.1;
  namespace "urn:m";
  prefix m;

  container top {
    leaf mode {
      type string;
      default "auto";
    }
    leaf manual-value {
      type uint8;
      must "../mode = 'manual'";
    }
  }
}
