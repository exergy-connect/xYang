module m {
  yang-version 1.1;
  namespace "urn:m";
  prefix m;

  feature f;
  feature g;

  container top {
    leaf a { if-feature "f"; type string; }
    leaf b { if-feature "f or g"; type string; }
    leaf c { if-feature "not f"; type string; }
    leaf d { if-feature "f and g"; type string; }
    list items {
      if-feature "f";
      key id;
      leaf id { type string; }
    }
  }
}
