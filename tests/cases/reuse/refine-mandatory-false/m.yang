module m {
  yang-version 1.1;
  namespace "urn:m";
  prefix m;

  grouping g {
    leaf entity {
      type string;
      mandatory true;
    }
  }

  container c {
    uses g {
      refine entity {
        mandatory false;
      }
    }
  }
}
