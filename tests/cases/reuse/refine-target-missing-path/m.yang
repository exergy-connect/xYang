module m {
  yang-version 1.1;
  namespace "urn:m";
  prefix m;

  grouping g {
    leaf a { type string; }
  }

  container c {
    uses g {
      refine missing/list {
        max-elements 0;
      }
    }
  }
}
