module m {
  yang-version 1.1;
  namespace "urn:m";
  prefix m;

  grouping endpoint {
    leaf host { type string; }
    leaf port { type uint16; }
  }

  grouping server {
    uses endpoint;
    leaf name { type string; }
  }

  container top {
    uses server {
      refine port { mandatory true; }
    }
    container backup {
      uses endpoint;
    }
  }
}
