module m {
  yang-version 1.1;
  namespace "urn:m";
  prefix m;
  import ietf-yang-structure-ext { prefix sx; }
  import numbers { prefix num; }
  sx:structure msg {
    leaf n { type num:small; default 5; }
  }
}
