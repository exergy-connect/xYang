module m {
  yang-version 1.1;
  namespace "urn:m";
  prefix m;

  container top {
    choice addr {
      mandatory true;
      leaf ipv4 { type string; }
      leaf ipv6 { type string; }
    }
    choice auth {
      case password {
        leaf user { type string; }
        leaf secret { type string; mandatory true; }
      }
      case none {
        leaf anonymous { type empty; }
      }
    }
  }
}
