module m {
  yang-version 1.1;
  namespace "urn:m";
  prefix m;

  container root {
    choice outer {
      mandatory true;
      case inner_wrap {
        choice inner {
          mandatory true;
          case a_case {
            leaf primitive {
              type string;
            }
          }
          case b_case {
            leaf other {
              type string;
            }
          }
        }
      }
      case c_case {
        leaf alt {
          type string;
        }
      }
    }
  }
}
