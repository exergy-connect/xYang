module m {
  yang-version 1.1;
  namespace "urn:m";
  prefix m;

  typedef change-history-policy {
    type union {
      type uint32;
      type string {
        pattern '\*';
      }
    }
  }

  container top {
    leaf change_history_policy {
      type change-history-policy;
      default 3;
    }
  }
}
