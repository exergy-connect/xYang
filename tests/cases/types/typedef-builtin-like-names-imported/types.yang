module types {
  yang-version 1.1;
  namespace "urn:types";
  prefix t;

  typedef date-and-time {
    type string { pattern '\d{4}-\d{2}-\d{2}T\d{2}:\d{2}:\d{2}Z'; }
  }
  typedef date {
    type string { pattern '\d{4}-\d{2}-\d{2}'; }
  }
}
