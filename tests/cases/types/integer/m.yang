module m {
  yang-version 1.1;
  namespace "urn:m";
  prefix m;

  container top {
    leaf u8 { type uint8; }
    leaf u16 { type uint16; }
    leaf u32 { type uint32; }
    leaf i8 { type int8; }
    leaf i16 { type int16; }
    leaf i32 { type int32; }
    leaf small { type int8 { range "-10..10"; } }
    leaf multi { type int32 { range "1..3 | 10..max"; } }
    leaf big { type int64; }
  }
}
