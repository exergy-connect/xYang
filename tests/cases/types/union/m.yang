module m {
  yang-version 1.1;
  namespace "urn:m";
  prefix m;

  container top {
    leaf limit {
      type union {
        type int8;
        type enumeration { enum unlimited; }
      }
    }
  }
}
