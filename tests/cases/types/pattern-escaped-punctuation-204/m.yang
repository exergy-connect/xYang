module m {
  yang-version 1.1;
  namespace "urn:m";
  prefix m;

  container top {
    leaf marks {
      type string {
        pattern '[b\*\-\#$@&:]+';
      }
    }
    leaf coded {
      type string {
        pattern 'a\#b\%c';
      }
    }
  }
}
