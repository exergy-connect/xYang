module m {
  yang-version 1.1;
  namespace "urn:m";
  prefix m;

  typedef primitive-type {
    type enumeration {
      enum string;
      enum integer;
      enum number;
      enum boolean;
    }
  }

  typedef composite-type {
    type enumeration {
      enum composite;
    }
  }

  typedef field-type {
    type union {
      type primitive-type;
      type composite-type;
    }
  }

  container data {
    leaf type {
      type field-type;
      mandatory true;
    }
  }
}
