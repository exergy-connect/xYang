module m {
  yang-version 1.1; namespace "urn:m"; prefix m;
  container a {
    leaf value { type code; }
    container child { leaf value { type code; } }
    typedef code { type string { pattern 'a+'; } }
  }
  container b {
    typedef code { type uint8 { range '1..5'; } }
    leaf value { type code; }
  }
}
