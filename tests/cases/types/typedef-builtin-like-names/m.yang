module m {
  yang-version 1.1;
  namespace "urn:m";
  prefix m;

  typedef date {
    type string { pattern '\d{4}-\d{2}-\d{2}'; }
  }
  typedef date-and-time {
    type string { pattern '\d{4}-\d{2}-\d{2}T\d{2}:\d{2}:\d{2}Z'; }
  }
  typedef this-year {
    type date { pattern '2026-.*'; }
  }
  typedef identifier {
    type string { pattern '[a-z]+'; length "1..8"; }
  }

  container top {
    leaf d { type date; }
    leaf dt { type date-and-time; }
    leaf this-year { type this-year; }
    leaf id { type identifier; }
    leaf refined { type date { pattern '2026-.*'; } }
  }
}
