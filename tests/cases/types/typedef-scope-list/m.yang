module m {
 yang-version 1.1; namespace "urn:m"; prefix m;
container top { list row {
 key id; leaf id { type string; }
 typedef code { type uint8 { range '1..5'; } }
 leaf-list values { type code; }
} }
}
