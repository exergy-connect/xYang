module m {
  yang-version 1.1;
  namespace "urn:m";
  prefix m;

  container top {
    leaf perms {
      type bits {
        bit read;
        bit write;
      }
    }
    leaf blob { type binary { length "1..4"; } }
  }
}
