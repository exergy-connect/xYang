module m {
  yang-version 1.1;
  namespace "urn:m";
  prefix m;

  feature f;

  container top {
    leaf a {
      if-feature f;
      type string;
    }
    leaf b {
      if-feature m:f;
      type string;
    }
  }
}
