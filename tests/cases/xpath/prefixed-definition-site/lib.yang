module lib {
  yang-version 1.1;
  namespace "urn:lib";
  prefix l;

  import base { prefix bs; }

  typedef item-ref {
    type leafref { path "/bs:top/bs:item/bs:n"; }
  }

  grouping picks {
    leaf gref {
      type leafref { path "/bs:top/bs:item/bs:n"; }
    }
    leaf gmust {
      type string;
      must "/bs:top/bs:item[bs:n = current()]" {
        error-message "gmust must name an item.";
      }
    }
  }
}
