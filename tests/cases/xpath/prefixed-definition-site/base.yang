module base {
  yang-version 1.1;
  namespace "urn:base";
  prefix base;

  container top {
    list item {
      key n;
      leaf n { type string; }
    }
    leaf where { type instance-identifier; }
  }
}
