module m {
  yang-version 1.1;
  namespace "urn:m";
  prefix m;

  import lib { prefix lb; }

  container sys {
    leaf name { type string; }
    list iface {
      key name;
      leaf name { type string; }
      leaf mtu { type uint16; }
    }
  }

  container top {
    uses lb:endpoint;
    leaf ifref {
      type leafref { path "/m:sys/m:iface/m:name"; }
    }
    leaf mtu-copy {
      type uint16;
      must ". = /m:sys/m:iface[m:name = current()/../m:ifref]/m:mtu" {
        error-message "mtu-copy must equal the mtu of ifref.";
      }
    }
    leaf core-only {
      when "/m:sys/m:name = 'core'";
      type string;
    }
  }
}
