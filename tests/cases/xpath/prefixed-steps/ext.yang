module ext {
  yang-version 1.1;
  namespace "urn:ext";
  prefix e;

  import m { prefix mm; }

  augment "/mm:sys" {
    leaf name { type string; }
    leaf tag {
      type string;
      must "../e:name != ../mm:name" {
        error-message "ext name must differ from m name.";
      }
    }
    leaf iref {
      type leafref { path "../mm:iface/mm:name"; }
    }
    leaf core-flag {
      when "../mm:name = 'core'";
      type string;
    }
  }
}
