module m {
  yang-version 1.1;
  namespace "urn:m";
  prefix m;

  container top {
    leaf plus { type int32; must ". + 1 = 3"; }
    leaf minus { type int32; must ". - 1 = 1"; }
    leaf times { type int32; must ". * 3 = 6"; }
    leaf text { type string; must ". + 'x' = 'ax'"; }
  }
}
