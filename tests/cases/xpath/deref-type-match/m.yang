module m {
  yang-version 1.1;
  namespace "urn:m";
  prefix m;

  container data-model {
    leaf consolidated {
      type boolean;
      default false;
    }
    list entities {
      key name;
      leaf name { type string; }
      leaf-list primary_key { type string; }
      list fields {
        key name;
        leaf name { type string; }
        leaf type { type string; }
        list foreignKeys {
          key entity;
          must "/data-model/consolidated = false() or ../type = deref(current()/entity)/../fields[name = deref(current()/entity)/../primary_key]/type" {
            error-message "Foreign key field type must match the referenced entity's primary key field type";
          }
          leaf entity {
            type leafref {
              path "/data-model/entities/name";
              require-instance true;
            }
            mandatory true;
          }
        }
      }
    }
  }
}
