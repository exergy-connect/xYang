module m {
  yang-version 1.1;
  namespace "urn:m";
  prefix m;

  container top {
    must "count(m:*) <= 1";
    must "count(*) >= count(m:*)";
    leaf a { type string; }
    leaf b { type string; }
  }
}
