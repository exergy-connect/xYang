module m {
  yang-version 1.1;
  namespace "urn:m";
  prefix m;

  import ietf-yang-structure-ext { prefix sx; }

  feature extra;

  sx:structure msg {
    leaf n {
      type uint8 {
        range "0..10";
      }
    }
    leaf enabled {
      type string;
    }
    container box {
      leaf id {
        type string;
      }
    }
  }

  sx:augment-structure "/m:msg" {
    if-feature "extra";
    when "enabled = 'on'";
    leaf extra-leaf {
      type string;
    }
  }

  sx:augment-structure "/m:msg/m:box" {
    leaf note {
      type string;
      must "string-length(.) > 0" {
        error-message "empty";
      }
    }
  }
}
