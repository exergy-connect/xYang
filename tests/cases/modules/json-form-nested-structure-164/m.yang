module m {
  yang-version 1.1;
  namespace "urn:m";
  prefix m;

  import ietf-yang-structure-ext { prefix sx; }

  sx:structure msg {
    container outer {
      list row {
        key "id";
        leaf id {
          type string;
        }
        leaf n {
          type uint8 {
            range "1..3";
          }
        }
        leaf ref {
          type leafref {
            path "../id";
          }
        }
      }
    }
    sx:structure inner {
      leaf b {
        type uint8;
      }
    }
  }
}
