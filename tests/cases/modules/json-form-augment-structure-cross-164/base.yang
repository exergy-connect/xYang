module base {
  yang-version 1.1;
  namespace "urn:base";
  prefix b;

  import ietf-yang-structure-ext { prefix sx; }

  sx:structure msg {
    container box {
      leaf id {
        type string;
      }
    }
    leaf n {
      type uint8;
    }
  }
}
