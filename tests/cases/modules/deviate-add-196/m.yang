module m {
  yang-version 1.1;
  namespace "urn:m";
  prefix m;

  leaf l { type string; }

  leaf check {
    type string;
    must "../l = 'x'" {
      error-message "need x";
    }
  }

  deviation "/m:l" {
    deviate add {
      default "x";
    }
  }
}
