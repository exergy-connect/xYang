module m {
  yang-version 1.1;
  namespace "urn:m";
  prefix m;

  container top {
    leaf a { type string; }
    leaf b { type uint8; }
  }

  deviation "/m:top/m:a" {
    deviate not-supported;
  }
}
