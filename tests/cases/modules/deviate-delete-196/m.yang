module m {
  yang-version 1.1;
  namespace "urn:m";
  prefix m;

  leaf l {
    type string;
    must ". = 'x'" {
      error-message "need x";
    }
  }

  deviation "/m:l" {
    deviate delete {
      must ". = 'x'";
    }
  }
}
