module m {
  yang-version 1.1;
  namespace "urn:m";
  prefix m;
  import base { prefix b; }
  identity widget { base b:thing; }
  identity plain;
  container top {
    uses b:g;
    leaf own { type identityref { base b:thing; } }
  }
}
