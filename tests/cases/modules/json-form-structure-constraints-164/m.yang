module m {
  yang-version 1.1;
  namespace "urn:m";
  prefix m;

  import ietf-yang-structure-ext { prefix sx; }

  sx:structure msg {
    leaf n {
      type uint8 {
        range "0..10";
      }
      mandatory true;
      must ". != 7" {
        error-message "not seven";
      }
    }
    leaf-list tags {
      type string {
        length "1..4";
      }
      min-elements 1;
    }
  }
}
