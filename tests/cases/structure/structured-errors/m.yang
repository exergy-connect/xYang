module m {
  yang-version 1.1;
  namespace "urn:m";
  prefix m;

  container top {
    leaf u8 {
      type uint8;
    }
    list items {
      key "id";
      leaf id {
        type string;
      }
      leaf v {
        type int32;
      }
    }
    leaf n {
      type int32;
      must ". >= 0";
    }
  }
}
