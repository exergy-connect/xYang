module m {
  yang-version 1.1;
  namespace "urn:m";
  prefix m;

  container top {
    list items {
      key id;
      min-elements 1;
      max-elements 2;
      leaf id { type string; }
    }
    leaf-list tags {
      type string { length "1..3"; }
      max-elements 2;
    }
  }
}
