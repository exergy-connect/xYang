module m {
  yang-version 1.1;
  namespace "urn:m";
  prefix m;

  container top {
    list servers {
      key name;
      unique "ip";
      leaf name { type string; }
      leaf ip { type string; }
    }
    list endpoints {
      key name;
      unique "m:ip port";
      leaf name { type string; }
      leaf ip { type string; }
      leaf port { type uint16; }
    }
  }
}
