module m {
  yang-version 1.1;
  namespace "urn:m";
  prefix m;

  container top {
    list items {
      key id;
      leaf id { type string; }
      leaf v { type int8 { range "0..10"; } }
    }
    list pairs {
      key "a b";
      leaf a { type string; }
      leaf b { type uint8; }
    }
  }
}
