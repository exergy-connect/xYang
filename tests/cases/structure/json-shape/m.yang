module m {
  yang-version 1.1;
  namespace "urn:m";
  prefix m;

  container top {
    container inner {
      leaf a { type string; }
    }
    list items {
      key id;
      leaf id { type string; }
    }
    leaf-list tags { type string; }
  }
}
