module m {
  yang-version 1.1;
  namespace "urn:m";
  prefix m;

  container top {
    leaf name { type string; mandatory true; }
    leaf note { type string; }
  }

  container opt {
    presence "enables the option";
    leaf level { type uint8; mandatory true; }
  }
}
