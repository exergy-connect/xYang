module m {
  yang-version 1.1;
  namespace "urn:m";
  prefix m;

  feature f;

  container root {
    list items {
      key name;
      leaf name {
        if-feature "f";
        type string;
      }
      leaf value {
        type string;
      }
    }
  }
}
