module m {
  yang-version 1.1;
  namespace "urn:m";
  prefix m;

  typedef node-name {
    type string { pattern "[a-z][a-z0-9]*"; }
  }

  rpc add-link {
    input {
      leaf source {
        type node-name;
        mandatory true;
      }
      leaf target {
        type node-name;
        mandatory true;
        must ". != ../source" {
          error-message "A link cannot connect a node to itself.";
        }
      }
      leaf weight {
        type uint8 { range "1..100"; }
        default 10;
      }
      leaf-list tag { type string; }
      list endpoint {
        key name;
        leaf name { type node-name; }
        leaf port { type uint16; }
      }
      must "count(endpoint) < 3" {
        error-message "At most two endpoints.";
      }
    }
    output {
      leaf link-id {
        type string { length "1..8"; }
        mandatory true;
      }
      leaf cost {
        type uint32;
        must "/m:add-link/m:link-id != 'free' or . = 0" {
          error-message "A free link has no cost.";
        }
      }
    }
  }

  rpc ping {
  }
}
