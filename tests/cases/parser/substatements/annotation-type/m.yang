module m {
  yang-version 1.1;
  namespace "urn:m";
  prefix m;

  extension annotation {
    argument name;
  }

  m:annotation "origin" {
    type string;
  }

  container top {
    leaf a { type string; }
  }
}
