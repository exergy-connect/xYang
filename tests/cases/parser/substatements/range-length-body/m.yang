module m {
  yang-version 1.1;
  namespace "urn:m";
  prefix m;

  extension note {
    argument arg;
  }

  container top {
  leaf id {
    type uint16 {
      range "1..199" {
        description
          "The ID of a community attribute filter.";
        reference
          "RFC 7950";
        error-message "id out of range";
        error-app-tag "bad-id";
        m:note "kept";
      }
    }
  }

  leaf name {
    type string {
      length "1..3" {
        description
          "Short name.";
        error-message "bad length";
        error-app-tag "bad-len";
      }
    }
  }

  leaf plain {
    type uint8 {
      range "0..10";
    }
  }
  }
}
