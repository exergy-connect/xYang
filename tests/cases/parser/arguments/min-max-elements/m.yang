module m {
  yang-version 1.1;
  namespace "urn:m";
  prefix m;

  container top {
    leaf-list plain {
      type string;
      min-elements 1;
      max-elements 20;
    }
    leaf-list quoted {
      type string;
      min-elements "1";
      max-elements "20";
    }
    leaf-list open {
      type string;
      max-elements unbounded;
    }
    leaf-list open-quoted {
      type string;
      max-elements "unbounded";
    }
  }
}
