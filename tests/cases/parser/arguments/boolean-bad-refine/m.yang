module m {
  yang-version 1.1;
  namespace "urn:m";
  prefix m;
  grouping g { leaf inner { type string; } }
  container top {
    uses g {
      refine inner {
        mandatory "yes";
      }
    }
  }
}
