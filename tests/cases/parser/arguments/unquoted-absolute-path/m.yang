module m {
  yang-version 1.1;
  namespace "urn:m";
  prefix m;

  container top {
    leaf a { type string; }
  }

  augment /m:top {
    leaf u { type string; }
  }

  augment "/m:top" {
    leaf q { type string; }
  }
}
