module m {
  yang-version 1.1;
  namespace "urn:m";
  prefix m;

  container top {
    leaf plain {
      type string { length 1..127; }
    }
    leaf quoted {
      type string { length "1..127"; }
    }
  }
}
