module m {
  yang-version 1.1;
  namespace "urn:m";
  prefix m;

  container data {
    list items {
      key "name";
      ordered-by user;
      leaf name {
        type string;
      }
    }
    leaf-list tags {
      type string;
      ordered-by system;
    }
  }
}
