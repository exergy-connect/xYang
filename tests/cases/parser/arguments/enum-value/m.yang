module m {
  yang-version 1.1;
  namespace "urn:m";
  prefix m;

  container top {
    leaf a {
      type enumeration {
        enum zero { value 0; }
        enum one { value "1"; }
      }
    }
  }
}
