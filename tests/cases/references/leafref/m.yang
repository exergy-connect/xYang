module m {
  yang-version 1.1;
  namespace "urn:m";
  prefix m;

  container top {
    list items {
      key id;
      leaf id { type string; }
    }
    leaf ref {
      type leafref { path "/top/items/id"; }
    }
    leaf rel {
      type leafref { path "../items/id"; }
    }
    leaf loose {
      type leafref {
        path "/top/items/id";
        require-instance false;
      }
    }
  }
}
