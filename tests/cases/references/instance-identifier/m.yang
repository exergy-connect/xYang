module m {
  yang-version 1.1;
  namespace "urn:m";
  prefix m;

  container top {
    leaf name { type string; }
    leaf target {
      type instance-identifier {
        require-instance true;
      }
    }
    leaf loose {
      type instance-identifier {
        require-instance false;
      }
    }
  }
}
