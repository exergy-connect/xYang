module m {
  yang-version 1.1;
  namespace "urn:m";
  prefix m;

  identity transport;
  identity tcp { base transport; }
  identity color;

  container top {
    leaf proto { type identityref { base transport; } }
  }
}
