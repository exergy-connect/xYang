module m {
  yang-version 1.1;
  namespace "urn:m";
  prefix m;

  list node {
    key id;
    leaf id { type string; }
    leaf one {
      type leafref { path "../../node/id"; }
    }
    container c {
      leaf-list many {
        type leafref { path "../../../node/id"; }
      }
    }
    leaf-list direct {
      type leafref { path "../../node/id"; }
    }
  }

  container top {
    list items {
      key id;
      leaf id { type string; }
    }
    leaf-list abs {
      type leafref { path "/top/items/id"; }
    }
  }
}
